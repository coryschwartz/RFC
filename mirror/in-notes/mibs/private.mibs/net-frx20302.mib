-- @(#)frx.mib	2.00 5/19/95
-- This is the enterprise specific MIB for NET's Frame Relay Exchange
-- (FRX) Copyright Network Equipment Technologies, Redwood City, CA
-- 94026.  Originally written by Todd E. Enersen, Dale Francisco, David
-- E. Swanson; January 1993.
--
-- G. Wayne: modified to support expanded port density and Software
-- Platform features.
--
-- Notable changes: 
-- 1.) Port number ranges modified from "0..31", to "0..255".
-- 2.) dsx1 MIB added. Supports DS1/E1 logical/physical instrumentation.
-- 3.) Traps added to support T1/E1 backcard alarms as well as many
--     types that anticipate near-term and planned changes.
-- 4.) Add T1/E1 and Token ring back card types.
-- 5.) Note that this MIB will be combined with the following MIB-2
--     groups via VxWorks:
--             system, interface, at, ip, icmp, udp, tcp.  This
--             instrumentation is part of the
--             configurable NMS option set provided with the WindNet
--             SNMP product (i.e. SNMP
--             Research agent and tools).

FRX-MIB DEFINITIONS ::= BEGIN

IMPORTS
	Counter, enterprises,
	Gauge, IpAddress				FROM RFC1155-SMI
	OBJECT-TYPE					FROM RFC-1212
	DisplayString					FROM RFC1213-MIB
	TRAP-TYPE					FROM RFC-1215;

net		OBJECT IDENTIFIER			::= { enterprises 177 }
spx		OBJECT IDENTIFIER			::= { net 1 }
lwx		OBJECT IDENTIFIER			::= { net 2 }
frx		OBJECT IDENTIFIER			::= { net 3 }
adaptive	OBJECT IDENTIFIER			::= { net 4 }
idnx		OBJECT IDENTIFIER			::= { net 5 }

globals		OBJECT IDENTIFIER			::= { frx 1 }
node		OBJECT IDENTIFIER			::= { frx 2 }
port		OBJECT IDENTIFIER			::= { frx 3 }
circuit		OBJECT IDENTIFIER			::= { frx 4 }
operator	OBJECT IDENTIFIER			::= { frx 5 }
event		OBJECT IDENTIFIER			::= { frx 6 }
network		OBJECT IDENTIFIER			::= { frx 7 }
management	OBJECT IDENTIFIER			::= { frx 8 }
gateway		OBJECT IDENTIFIER			::= { frx 9 }
dsx		OBJECT IDENTIFIER			::= { frx 10 }
filesystem	OBJECT IDENTIFIER			::= { frx 11 }


--
-- global variables
--

mibVersion						OBJECT-TYPE
	SYNTAX	INTEGER
	ACCESS	read-only
	STATUS	mandatory
	DESCRIPTION
		"The version number of this FRX MIB."
	::= { globals 1 }

mibEditVersion						OBJECT-TYPE
	SYNTAX	INTEGER
	ACCESS	read-only
	STATUS	mandatory
	DESCRIPTION
		"The edit version (sub version) number of this FRX MIB."
	::= { globals 2 }
--
-- The node parameters and status.
--
nodeIdnxAddress						OBJECT-TYPE
	SYNTAX DisplayString (SIZE(0..16))
	ACCESS read-only
	STATUS mandatory
	DESCRIPTION
		"The IDNX Address of this PX card, e.g. NxCy."
	::= { node 1 }

nodeSoftwareRelease					OBJECT-TYPE
	SYNTAX DisplayString (SIZE(0..80))
	ACCESS read-only
	STATUS mandatory 
	DESCRIPTION
		"The release of FRX code running on this PX card, e.g.
		 Release 2.01.01 Version 81.01." 
	::= { node 2 }

nodeSoftwareReleaseDate					OBJECT-TYPE
	SYNTAX DisplayString (SIZE(0..80))
	ACCESS read-only
	STATUS mandatory
	DESCRIPTION
		"The date the FRX code was built, e.g. Wed Feb 10 14:12:24
		 PST 1993 by tee." 
	::= { node 3 }

nodeBootVersion 					OBJECT-TYPE
	SYNTAX DisplayString (SIZE(0..80))
	ACCESS read-only
	STATUS mandatory
	DESCRIPTION
		"The version of boot prom on the PX card."
	::= { node 4 }

nodeCardType						OBJECT-TYPE
	SYNTAX DisplayString (SIZE(0..80))
	ACCESS read-only
	STATUS mandatory
	DESCRIPTION
		"The type of PX card running the FRX code."
	::= { node 5 }

nodeUpTime						OBJECT-TYPE
	SYNTAX DisplayString (SIZE(0..80))
	ACCESS read-only
	STATUS mandatory
	DESCRIPTION
		"The amount of time the FRX has been alive."
	::= { node 6 }

nodeCongestionLevel					OBJECT-TYPE
	SYNTAX  INTEGER {
	    	notCongested(1), 
		approachingCongestion(2),
		congested(3),
		fullyCongested(4)
		}
	ACCESS read-only
	STATUS mandatory
	DESCRIPTION
		"The current state of congestion for the FRX node. The
		 valid values are notCongested (normal operation),
		 approachingCongestion (FECN and BECN are being set),
		 congested (DE frames are being dropped), and
		 fullyCongested (normal data frames are being dropped)."   
		 
	::= { node 7 }

nodeBuffersUsed						OBJECT-TYPE
	SYNTAX	INTEGER (0..500)
	ACCESS 	read-only
	STATUS	mandatory
	DESCRIPTION
		"The number of system buffers being used."
	::= { node 8 }

nodeNumberHDLCPorts					OBJECT-TYPE
	SYNTAX 	INTEGER (4..128)
	ACCESS	read-only
	STATUS	mandatory
	DESCRIPTION
		"The number of HDLC ports the hardware supports."
	::= { node 9 }

nodeIPAddress						OBJECT-TYPE	
	SYNTAX	IpAddress
	ACCESS	read-only
	STATUS	mandatory
	DESCRIPTION
		"The IP Address of this FRX Node."
	::= { node 10 }

nodeNetworkMask						OBJECT-TYPE
	SYNTAX	IpAddress
	ACCESS	read-write
	STATUS	mandatory
	DESCRIPTION
		"The IP network mask for this FRX Node."
	::= { node 11 }

nodeBackcard						OBJECT-TYPE
	SYNTAX	INTEGER{
		disabled(1),
		enabled(2)
		}
	ACCESS	read-write
	STATUS	mandatory
	DESCRIPTION
		"Enables or disables the backcard on the FRX node. The
		 backcard must be enabled for gateway functionality. Note:
		 If the backcard is not physically present, an attempt to
		 enable it will result in an error."   
	::= { node 12 }

-- (EYA)
-- Changed the cardtyppe values to reflect what's in the
-- new IDNX 13.X3 release.
--
--nodeBackcardType					OBJECT-TYPE
--	SYNTAX	INTEGER {
--		ethernet(1),
--		unknown-invalid(2),
--		t1-e1-ethernet(3),
--		token-ring(4)
--		}
--	ACCESS	read-only
--	STATUS	mandatory
--	DESCRIPTION
--		"The type of backcard interface installed."
--	::= { node 13 }
--
nodeBackcardType					OBJECT-TYPE
	SYNTAX	INTEGER {
		ethernet(1),
		token-ring(2),
		t1(3),
		e1(4),
		t1-ethernet(5),
		e1-ethernet(6),
		dual-ethernet(7),
		ethernet-token-ring(8),
		quad-t1(9),
		quad-e1(10),
		none-unknown-invalid(11)
		}
	ACCESS	read-only
	STATUS	mandatory
	DESCRIPTION
		"The type of backcard interface installed."
	::= { node 13 }

nodeBackcardSerialNumber				OBJECT-TYPE
	SYNTAX	DisplayString (SIZE(1..25))
	ACCESS	read-only
	STATUS	mandatory
	DESCRIPTION
		"The serial number and revision of the backcard
		 interface."
	::= { node 14 }
	
nodeBillingDownloads					OBJECT-TYPE
	SYNTAX	INTEGER {
		disabled(1),
		enabled(2)
		}
	ACCESS	read-write
	STATUS	mandatory
	DESCRIPTION
		"Enables or disables billing record downloads to an NMS
		 workstation from this FRX node." 
	::= { node 15 }

nodeConfigurationDownloads				OBJECT-TYPE
	SYNTAX	INTEGER {
		disabled(1),
		enabled(2)
		}
	ACCESS	read-write
	STATUS	mandatory
	DESCRIPTION
		"Enables or disables configuration record downloads to an
		 NMS workstation from this FRX node." 
	::= { node 16 }

--
-- Re. Edman 27227
--
-- the access and status have been changed so that this variable
-- is not accessible anymore.
--
nodeFrameCounterThreshold				OBJECT-TYPE
	SYNTAX	INTEGER
	ACCESS	not-accessible
	STATUS	deprecated
	DESCRIPTION
		"A threshold that causes a billing record to be downloaded
		 when a frame counter exceeds its value." 
	::= { node 17 }

--
-- Re. Edman 27227
--
-- the access and status have been changed so that this variable
-- is not accessible anymore.
--
nodeByteCounterThreshold 				OBJECT-TYPE
	SYNTAX	INTEGER
	ACCESS	not-accessible
	STATUS	deprecated
	DESCRIPTION
		"A threshold that causes a billing record to be downloaded
		 when a byte counter exceeds its value." 
	::= { node 18 }

nodeBillingTimeTable					OBJECT-TYPE
	SYNTAX SEQUENCE OF NodeBillingTimeEntry
	ACCESS	not-accessible
	STATUS	mandatory
	DESCRIPTION
		"The list of times to download billing records to an NMS
		 workstation." 
	::= { node 19 }

nodeNMSWorkstationTable					OBJECT-TYPE
	SYNTAX SEQUENCE OF NodeNMSWorkstationEntry
	ACCESS	not-accessible
	STATUS	mandatory
	DESCRIPTION
		"The list of workstations that are downloaded with billing
		 and configuration records." 
	::= { node 20 }

nodeNumberTBUSPorts					OBJECT-TYPE
	SYNTAX 	INTEGER (4..32)
	ACCESS	read-only
	STATUS	mandatory
	DESCRIPTION
		"The number of TBus ports the hardware supports."
	::= { node 21 }

nodeBackcardWanIF					OBJECT-TYPE
	SYNTAX	INTEGER{
		disabled(1),
		enabled(2)
		}
	ACCESS	read-write
	STATUS	mandatory
	DESCRIPTION
		"Enables or disables the backcard WAN I/F  on the FRX node. The
		 backcard must be enabled for WAN port functionality. Note:
		 If the backcard is not physically present, an attempt to
		 enable it will result in an error."   
	::= { node 22 }

nodeAlarmedPorts					OBJECT-TYPE
	SYNTAX  Gauge
	ACCESS  read-only
	STATUS  mandatory
	DESCRIPTION
		"The number of front or backcard ports on this node where
		any of the following conditions is true:
		- portTBusState (or T1 Status for backcard ports) is 'down'
		- portUNIState is 'down'
		- portAlarmedPVCs is not zero."
	::= { node 23 }

nodeBillingTimeEntry					OBJECT-TYPE
	SYNTAX	NodeBillingTimeEntry
	ACCESS	not-accessible
	STATUS	mandatory
	DESCRIPTION
		"A row from the billing download time table."
	INDEX	{ downloadTimeIndex }
	::= { nodeBillingTimeTable 1 }

NodeBillingTimeEntry ::= 
	SEQUENCE { 
		downloadTime				OCTET STRING,
		downloadTimeRowStatus			INTEGER,
		downloadTimeIndex			INTEGER (0..86399)
	}

downloadTime						OBJECT-TYPE
	SYNTAX	OCTET STRING
	ACCESS	read-write
	STATUS	mandatory
	DESCRIPTION
		"A time of day at which billing records for the node are
		 sent to an NMS workstation." 
	::= { nodeBillingTimeEntry 1 }

downloadTimeRowStatus					OBJECT-TYPE
	SYNTAX	INTEGER {
		invalid(1),
		valid(2)
		}
	ACCESS	read-write
	STATUS	mandatory
	DESCRIPTION
		"Controls row deletion for this table. Setting to invalid
		 deletes the row from the table." 
	::= { nodeBillingTimeEntry 2 }

downloadTimeIndex					OBJECT-TYPE
	SYNTAX	INTEGER (0..86399)
	ACCESS	read-only
	STATUS	mandatory
	DESCRIPTION
		"The index into the billing time table."
	::= { nodeBillingTimeEntry 3 }

nodeNMSWorkstationEntry 				OBJECT-TYPE
	SYNTAX	NodeNMSWorkstationEntry
	ACCESS	not-accessible
	STATUS	mandatory	
	DESCRIPTION
		"A row from the NMS workstation download target list."
	INDEX	{ nmsWorkstationAddress }
	::= { nodeNMSWorkstationTable 1 }

NodeNMSWorkstationEntry ::=
	SEQUENCE {
		nmsWorkstationAddress			IpAddress,
		nmsWorkstationInetPort			INTEGER (0..65535),
		nmsWorkstationRowStatus			INTEGER
	}

nmsWorkstationAddress 					OBJECT-TYPE
	SYNTAX	IpAddress
	ACCESS	read-write
	STATUS	mandatory
	DESCRIPTION
		"The IP address of an NMS workstation that billing and
		 configuration records get downloaded to." 
	::= { nodeNMSWorkstationEntry 1 }

nmsWorkstationInetPort 					OBJECT-TYPE
	SYNTAX	INTEGER (0..65535)
	ACCESS	read-write
	STATUS	mandatory
	DESCRIPTION
		"The internet port on which the special TFTP server on an
		 NMS workstation will listen for requests to download
		 billing and configuration records."  
	::= { nodeNMSWorkstationEntry 2 }

nmsWorkstationRowStatus 				OBJECT-TYPE
	SYNTAX	INTEGER {
		invalid(1),
		valid(2)
		}
	ACCESS	read-write
	STATUS	mandatory
	DESCRIPTION
		"Controls row deletion for this table. Setting to invalid
		 deletes the row from the table." 
	::= { nodeNMSWorkstationEntry 3 }

portConfTable						OBJECT-TYPE
	SYNTAX SEQUENCE OF PortConfEntry
	ACCESS	not-accessible
	STATUS	mandatory
	DESCRIPTION
		"A table of this FRX's port configuration. Before
		 attempting to modify any variables in this table, the port
		 must be disabled (set portConfState = 'disable')."    
	::= { port 1 }

portConfEntry 						OBJECT-TYPE
	SYNTAX	PortConfEntry
	ACCESS	not-accessible
	STATUS	mandatory		
	DESCRIPTION
		"An entry (conceptual row) in the port configuration
		 table." 
	INDEX   { portConfEntryId }
	::= { portConfTable 1 }

PortConfEntry ::=
	SEQUENCE {
		portConfEntryId			INTEGER (0..255),
		portConfState			INTEGER,
		portInterfaceProtocol		INTEGER,
		portKeepaliveVerif		INTEGER,
		portBackupInterNodal		INTEGER,
		portExternalFrTrunk		INTEGER,
		portUniExternalFrTrunk		INTEGER,
		portDlciExternalFrTrunk		INTEGER (0..1023),
		portLinkIntegVerif		INTEGER,
		portAsyncPVCStatus		INTEGER,
		portN391Counter			INTEGER,
		portN392Counter			INTEGER,
		portN393Counter			INTEGER,
		portT391Timer			INTEGER,
		portT392Timer			INTEGER,
		portSdlcEncapMode		INTEGER,
		portSdlcEncapDefaultDlci	INTEGER (0..1023),
		portAddrMapDefaultDlci		INTEGER (0..1023),
		portPriorityQueuing		INTEGER,
		portAccountingPerDlci		INTEGER
		}

portConfEntryId					OBJECT-TYPE
	SYNTAX	INTEGER (0..255)
	ACCESS	read-only
	STATUS	mandatory
	DESCRIPTION
		"The port identifier (number) for this port."
	::= { portConfEntry 1 }

portConfState					OBJECT-TYPE
	SYNTAX	INTEGER {
		delete(1),
		install(2),
		disable(3),
		activate(4)
		}
	ACCESS	read-write
	STATUS	mandatory
	DESCRIPTION
		"Performs the enumerated action on the port. That is to
		 say, setting the value to delete will cause the port to be
		 deleted, etc. This variable must be set to 'disable'
		 before any other port configuration variables can be
		 modified."     
	::= { portConfEntry 2 }

portInterfaceProtocol				OBJECT-TYPE
	SYNTAX	INTEGER	{
		ansiNetwork(1),
		ansiUser(2),
		ansiNNI(3),
		ccittNetwork(4),
		ccittUser(5),
		ccittNNI(6),
		lmiNetwork(7),
		lmiUser(8),
		none(9),
		interNode(10),
		sdlcHdlcEncap(11)
		}
	ACCESS read-write
	STATUS mandatory
	DESCRIPTION
		"Determines the function of the port, including which UNI
		 protocol is to be used. All values except interNode are
		 for ports at access points into the network. InterNode is
		 for ports internal to the network. AnsiNetwork, ansiUser,
		 and ansiNNI conform to procedures specified in the ANSI
		 T1.617 Annex D specification. ccittNetwork, ccittUser, and
		 ccittNNI conform to procedures specified in the CCITT
		 Q.933 Annex A specification. lmiNetwork, lmiUser, and
		 lmiNNI conform to procedures specified in the DEC,
		 Northern Telecom, StratCom specification."         
	::= { portConfEntry 3 }

portKeepaliveVerif					OBJECT-TYPE
	SYNTAX	INTEGER {
		disabled(1),
		enabled(2)
		}
	ACCESS	read-write
	STATUS	mandatory
	DESCRIPTION
		"Enables or disables keepalive verification. This
		 parameter is applicable when the portInterfaceProtocol is
		 interNode."  
	::= { portConfEntry 4 }


portBackupInterNodal					OBJECT-TYPE
	SYNTAX	INTEGER {
		disabled(1),
		enabled(2)
		}
	ACCESS	read-write
	STATUS	mandatory
	DESCRIPTION
		"Enables or disables using this port as a backup
		 Inter-Nodal port. This parameter is applicable when the
		 portInterfaceProtocol is interNode."  
	::= { portConfEntry 5 }

portExternalFrTrunk					OBJECT-TYPE
	SYNTAX	INTEGER {
		disabled(1),
		enabled(2)
		}
	ACCESS	read-write
	STATUS	mandatory
	DESCRIPTION
		"Enables or disables the External Frame Relay Trunk
		 feature." 
	::= { portConfEntry 6 }

portUniExternalFrTrunk					OBJECT-TYPE
	SYNTAX	INTEGER {
		ansiUser(2),
		ccittUser(5),
		lmiUser(8),
		none(9)
		}
	ACCESS	read-write
	STATUS	mandatory
	DESCRIPTION
		"The UNI protocol to use when the External Frame Relay
		 Trunk feature is enabled." 
	::= { portConfEntry 7 }

portDlciExternalFrTrunk					OBJECT-TYPE
	SYNTAX	INTEGER (16..991)
	ACCESS	read-write
	STATUS	mandatory
	DESCRIPTION
		"The DLCI of the PVC that is in use at the UNI when the
		 External Frame Relay Trunk feature is enabled." 
	DEFVAL	{16}
	::= { portConfEntry 8 }

portLinkIntegVerif 					OBJECT-TYPE
	SYNTAX	INTEGER {
		disabled(1),
		enabled(2)
		}
	ACCESS read-write
	STATUS mandatory
	DESCRIPTION
		"Determines whether this port will react to problems
		 detected by a UNI protocol. This parameter is applicable
		 if the portInterfaceProtocol is ansi*, ccitt*, or lmi*."  
	::= { portConfEntry 9 }

portAsyncPVCStatus					OBJECT-TYPE
	SYNTAX	INTEGER {
		disabled(1),
		enabled(2)
		}
	ACCESS read-write
	STATUS mandatory
	DESCRIPTION
		"Determines whether this port should send Asynchronous PVC
		 status messages. This parameter is applicable if the
		 portInterfaceProtocol is ansiNetwork, ansiNNI,
		 ccittNetwork, or ccittNNI."   
	::= { portConfEntry 10 }
	
portN391Counter						OBJECT-TYPE
	SYNTAX	INTEGER (1..255)
	ACCESS  read-write
	STATUS	mandatory
	DESCRIPTION
		"The value for N391, the full status polling counter."
	::= { portConfEntry 11 }

portN392Counter						OBJECT-TYPE
	SYNTAX	INTEGER (1..10)
	ACCESS  read-write
	STATUS	mandatory
	DESCRIPTION
		"The value for N392, the error threshold counter."
	::= { portConfEntry 12 }

portN393Counter						OBJECT-TYPE
	SYNTAX	INTEGER (1..10)
	ACCESS  read-write
	STATUS	mandatory
	DESCRIPTION
		"The value for N393, the monitored events counter."
	::= { portConfEntry 13 }

portT391Timer						OBJECT-TYPE
	SYNTAX	INTEGER (5..30)
	ACCESS  read-write
	STATUS	mandatory
	DESCRIPTION
		"The value for T391, the link integrity polling timer."
	::= { portConfEntry 14 }

portT392Timer						OBJECT-TYPE
	SYNTAX	INTEGER (5..30)
	ACCESS  read-write
	STATUS	mandatory
	DESCRIPTION
		"The value for T392, the polling verification timer."
	::= { portConfEntry 15 }

portSdlcEncapMode					OBJECT-TYPE
	SYNTAX	INTEGER {
		transparent(1),
		addressMapped(2)
		}
	ACCESS	read-write
	STATUS	mandatory
	DESCRIPTION
		"Selects which encapsulation mode to be used when the
		 portInterfacePrococol is sdlcHdlcEncap." 
	::= { portConfEntry 16 }

portSdlcEncapDefaultDlci				OBJECT-TYPE
	SYNTAX	INTEGER (16..991)
	ACCESS	read-write
	STATUS	mandatory
	DESCRIPTION
		"Specifies which DLCI will be used to encapsulate received
		 SDLC/HDLC frames at the entry to the network. This
		 parameter is applicable if the portInterfaceProtocol is
		 sdlcHdlcEncap and the encapsulation mode is transparent." 
		  
	DEFVAL	{16}
	::= { portConfEntry 17 }


portAddrMapDefaultDlci					OBJECT-TYPE
	SYNTAX	INTEGER (1..991)
	ACCESS	read-write
	STATUS	mandatory
	DESCRIPTION
		"Specifies which DLCI will be used to encapsulate received
		 SDLC/HDLC frames at the entry to the network. This
		 parameter is applicable if the portInterfaceProtocol is
		 sdlcHdlcEncap and the encapsulation mode is
		 address-mapped."   
	DEFVAL	{16}
	::= { portConfEntry 18 }

portPriorityQueuing					OBJECT-TYPE
	SYNTAX	INTEGER {
		disabled(1),
		enabled(2)	
		}
	ACCESS	read-write
	STATUS	mandatory
	DESCRIPTION
		"Enables or disables priority queuing on a port."
	::= { portConfEntry 19 }

portAccountingPerDlci					OBJECT-TYPE
	SYNTAX	INTEGER {
		disabled(1),
		enabled(2)	
		}
	ACCESS	read-write
	STATUS	mandatory
	DESCRIPTION
		"Enables or disables accounting per DLCI on a port.
		 Enabling this feature may seriously degrade performance in
		 systems with high speed (greater than 1.024 Mbps) ports.
		 Frames may be lost."   
	::= { portConfEntry 20 }

portStatusTable						OBJECT-TYPE
	SYNTAX SEQUENCE OF PortStatusEntry
	ACCESS	not-accessible
	STATUS	mandatory
	DESCRIPTION
		"A table of this node's port status and statistics."
	::= { port 2 }

portStatusEntry						OBJECT-TYPE
	SYNTAX	PortStatusEntry
	ACCESS	not-accessible
	STATUS	mandatory
	DESCRIPTION
		"The port status and statistics table."
	INDEX   { portStatusEntryId }
	::= { portStatusTable 1 }

PortStatusEntry ::=
	SEQUENCE {
		portDataBaseState		INTEGER,
		portTBusState			INTEGER,
		portUNIState			INTEGER,
		portNumberEstablishedCircuits	INTEGER,
		portNumberTotalCircuits		INTEGER,
		portRxCongestState		INTEGER,
		portTxCongestState		INTEGER,
		portAccessRate			INTEGER,
		portCIR				INTEGER,
		portNeighbor			DisplayString,
		portInFrames			Counter,
		portOutFrames			Counter,
		portInBytes			Counter,
		portOutBytes			Counter,
		portDroppedFrames		Counter,
		portDroppedDEFrames		Counter,
		portUnknownDLCIFrames		Counter,
		portLastUnknownDLCI		INTEGER (0..1023),
		portDEInFrames			Counter,
		portDEOutFrames			Counter,
		portDEInBytes			Counter,
		portDEOutBytes			Counter,
		portBECNInFrames		Counter,
		portBECNOutFrames		Counter,
		portFECNInFrames 		Counter,
		portFECNOutFrames		Counter,
		portFrameRateIn			Gauge,
		portFrameRateOut		Gauge,
		portByteRateIn			Gauge,
		portByteRateOut			Gauge,
		portAverageRxQueue		Gauge,
		portAverageTxQueue		Gauge,
		portMaxFrameRateIn		Gauge,
		portMaxFrameRateOut		Gauge,
		portMaxByteRateIn		Gauge,
		portMaxByteRateOut		Gauge,
		portMaxQueueDepthIn		Gauge,
		portMaxQueueDepthOut		Gauge,
		portBadFrames			Counter,
		portShortFrames			Counter,
		portMissedFrames		Counter,
		portLongFrames			Counter,
		portRxOverruns			Counter,
		portTxUnderruns			Counter,
		portStatusEntryId		INTEGER,		
		portStatsClearedTime		DisplayString,
		portDropBWadmitFrames		Counter,
		portDropInCongestFrames		Counter,
		portDropOutCongestFrames	Counter,
		portDropErroredFrames		Counter,
		portDropPVCinactiveFrames	Counter,
		portDropPortDisabledFrames	Counter,
		portChannelAssignment		INTEGER,
		portAlarmedPVCs			Gauge
	}

portDataBaseState					OBJECT-TYPE
	SYNTAX	INTEGER {
		installed(1),
		active(2)
		}
	ACCESS	read-only
	STATUS	mandatory
	DESCRIPTION
		"The state of the port in the database. The values are
		 active and disabled." 
	::= { portStatusEntry 1 }

portTBusState						OBJECT-TYPE
	SYNTAX	INTEGER {
		down(1),
		up(2)
		}
	ACCESS	read-only
	STATUS	mandatory
	DESCRIPTION
		"The state of the TBus connection for this port. The
		 values are up and down." 
	::= { portStatusEntry 2 }

portUNIState						OBJECT-TYPE
	SYNTAX	INTEGER {
		down(1),
		up(2),
		invalid(3)
		}
	ACCESS	read-only
	STATUS	mandatory
	DESCRIPTION
		"The state of the UNI for this port. The valid values are
		 up and down." 
	::= { portStatusEntry 3 }

portNumberEstablishedCircuits				OBJECT-TYPE
	SYNTAX 	INTEGER
	ACCESS	read-only
	STATUS	mandatory
	DESCRIPTION
		"The number of virtual circuits on this port in state
		 Complete." 
	::= { portStatusEntry 4 }

portNumberTotalCircuits					OBJECT-TYPE
	SYNTAX 	INTEGER
	ACCESS	read-only
	STATUS	mandatory
	DESCRIPTION
		"The total number of virtual circuits on this port,
		 regardles of state." 
	::= { portStatusEntry 5 }

portRxCongestState					OBJECT-TYPE
	SYNTAX	INTEGER {
		notCongested(1),
		approachingCongestion(2),
		congested(3),
		fullyCongested(4)
		}
	ACCESS	read-only
	STATUS	mandatory
	DESCRIPTION
		"The congestion state of the port's receiver. The valid
		 values are notCongested (normal operation),
		 approachingCongestion (FECN and BECN are being set),
		 congested (DE frames are being dropped), and
		 fullyCongested (normal data frames are being dropped)."   
		 
	::= { portStatusEntry 6 }

portTxCongestState					OBJECT-TYPE
	SYNTAX	INTEGER {
		notCongested(1),
		approachingCongestion(2),
		congested(3),
		fullyCongested(4)
		}
	ACCESS	read-only
	STATUS	mandatory
	DESCRIPTION
		"The congestion state of the port's transmitter. The valid
		 values are notCongested (normal operation),
		 approachingCongestion (FECN and BECN are being set),
		 congested (DE frames are being dropped), and
		 fullyCongested (normal data frames are being dropped)."   
		 
	::= { portStatusEntry 7 }

portAccessRate						OBJECT-TYPE 
	SYNTAX	INTEGER 
	ACCESS	read-only
	STATUS	mandatory
	DESCRIPTION
		"The access rate (speed) for this port in bits per
		 second."
	::= { portStatusEntry 8 }

portCIR							OBJECT-TYPE
	SYNTAX 	INTEGER
	ACCESS	read-only
	STATUS	mandatory
	DESCRIPTION
		"The total allocated committed information rate for all
		 virtual circuits on this port." 
	::= { portStatusEntry 9 }

portNeighbor						OBJECT-TYPE
	SYNTAX 	DisplayString(SIZE(0..80))
	ACCESS	read-only
	STATUS	mandatory
	DESCRIPTION
		"Represents the IDNX domain-node-card of the adjacent FRX.
		 This field is valid for ports with the interface protocol
		 set to interNode. "  
	::= { portStatusEntry 10 }

portInFrames						OBJECT-TYPE
	SYNTAX	Counter
	ACCESS	read-only
	STATUS	mandatory
	DESCRIPTION
		"The number of frames received by this port."
	::= { portStatusEntry 11 }

portOutFrames						OBJECT-TYPE
	SYNTAX	Counter
	ACCESS	read-only
	STATUS	mandatory
	DESCRIPTION
		"The number of frames transmitter by this port."
	::= { portStatusEntry 12 }
	
portInBytes						OBJECT-TYPE
	SYNTAX	Counter
	ACCESS	read-only
	STATUS	mandatory
	DESCRIPTION
		"The number of bytes received by this port."
	::= { portStatusEntry 13 }

portOutBytes						OBJECT-TYPE
	SYNTAX	Counter
	ACCESS	read-only
	STATUS	mandatory
	DESCRIPTION
		"The number of bytes transmitted by this port."
	::= { portStatusEntry 14 }

portDroppedFrames					OBJECT-TYPE
	SYNTAX	Counter
	ACCESS	read-only
	STATUS	mandatory
	DESCRIPTION
		"The number of frames dropped by the port for reasons
		other than: DE, unknown DLCI, bandwidth admission, 
		input/output congestion, frame error, inactive PVC,
		or disabled port.  These are generally internal 
		errors, such as 'Heap buffer failed'." 
	::= { portStatusEntry 15 }

portDroppedDEFrames					OBJECT-TYPE
	SYNTAX	Counter
	ACCESS	read-only
	STATUS	mandatory
	DESCRIPTION
		"The number of frames with DE set dropped due to
		 congestion." 
	::= { portStatusEntry 16 }

portUnknownDLCIFrames					OBJECT-TYPE
	SYNTAX	Counter
	ACCESS	read-only
	STATUS	mandatory
	DESCRIPTION
		"The number of frames received with unknown DLCIs."
	::= { portStatusEntry 17 }

portLastUnknownDLCI					OBJECT-TYPE
	SYNTAX	INTEGER (16..991)
	ACCESS	read-only
	STATUS	mandatory
	DESCRIPTION
		"The DLCI number of the last frame with an unknown DLCI. A
		 value of -1 signifies that no unknown DLCI has yet been
		 received."  
	::= { portStatusEntry 18 }

portDEInFrames						OBJECT-TYPE
	SYNTAX	Counter
	ACCESS	read-only
	STATUS	mandatory
	DESCRIPTION
		"The number of DE frames received by a port."
	::= { portStatusEntry 19 }

portDEOutFrames						OBJECT-TYPE
	SYNTAX	Counter
	ACCESS	read-only
	STATUS	mandatory
	DESCRIPTION
		"The number of DE frames transmitted by a port."
	::= { portStatusEntry 20 }

portDEInBytes						OBJECT-TYPE
	SYNTAX	Counter
	ACCESS	read-only
	STATUS	mandatory
	DESCRIPTION
		"The number of bytes received in DE frames."
	::= { portStatusEntry 21 }

portDEOutBytes						OBJECT-TYPE
	SYNTAX	Counter
	ACCESS	read-only
	STATUS	mandatory
	DESCRIPTION
		"The number of bytes transmitted in DE frames."
	::= { portStatusEntry 22 }

portBECNInFrames					OBJECT-TYPE
	SYNTAX	Counter
	ACCESS	read-only
	STATUS	mandatory
	DESCRIPTION
		"The number of BECN frames received by a port."
	::= { portStatusEntry 23 }

portBECNOutFrames					OBJECT-TYPE
	SYNTAX	Counter
	ACCESS	read-only
	STATUS	mandatory
	DESCRIPTION
		"The number BECN frames transmitted by a port."
	::= { portStatusEntry 24 }

portFECNInFrames					OBJECT-TYPE
	SYNTAX	Counter
	ACCESS	read-only
	STATUS	mandatory
	DESCRIPTION
		"The number of FECN frames received by a port."
	::= { portStatusEntry 25 }

portFECNOutFrames					OBJECT-TYPE
	SYNTAX	Counter
	ACCESS	read-only
	STATUS	mandatory
	DESCRIPTION
		"The number of FECN frames transmitted by a port."
	::= { portStatusEntry 26 }

portFrameRateIn						OBJECT-TYPE
	SYNTAX	Gauge
	ACCESS	read-only
	STATUS	mandatory
	DESCRIPTION
		"The rate in frames per second of frames received by the
		 FRX. This number is a updated every minute and represents
		 the last five minutes worth of traffic."  
	::= { portStatusEntry 27 }
	
portFrameRateOut					OBJECT-TYPE
	SYNTAX	Gauge
	ACCESS	read-only
	STATUS	mandatory
	DESCRIPTION
		"The rate in frames per second of frames transmitted by
		 the FRX. This number is a updated every minute and
		 represents the last five minutes worth of traffic."  
	::= { portStatusEntry 28 }

portByteRateIn						OBJECT-TYPE
	SYNTAX	Gauge
	ACCESS 	read-only
	STATUS	mandatory
	DESCRIPTION
		"The rate in bytes per second received by the FRX. This
		 number is updated every minute and represents the last
		 five minutes worth of traffic."  
	::= { portStatusEntry 29 }

portByteRateOut						OBJECT-TYPE
	SYNTAX	Gauge
	ACCESS 	read-only
	STATUS	mandatory
	DESCRIPTION
		"The rate in bytes per second received by the FRX. This
		 number is updated every minute and represents the last
		 five minutes worth of traffic."  
	::= { portStatusEntry 30}

portAverageRxQueue					OBJECT-TYPE
	SYNTAX	Gauge
	ACCESS	read-only
	STATUS	mandatory
	DESCRIPTION
		"The average depth of the receiver's input queue."
	::= { portStatusEntry 31 }

portAverageTxQueue					OBJECT-TYPE
	SYNTAX	Gauge
	ACCESS	read-only
	STATUS	mandatory
	DESCRIPTION
		"The average depth of the transmitter's output queue."
	::= { portStatusEntry 32 }

portMaxFrameRateIn					OBJECT-TYPE
	SYNTAX	Gauge
	ACCESS	read-only
	STATUS	mandatory
	DESCRIPTION
		"The maximum frame rate for frames received by a port."
	::= { portStatusEntry 33 }

portMaxFrameRateOut					OBJECT-TYPE
	SYNTAX 	Gauge
	ACCESS	read-only
	STATUS	mandatory
	DESCRIPTION
		"The maximum frame rate for frames transmitted by a port."
	::= { portStatusEntry 34 }

portMaxByteRateIn					OBJECT-TYPE
	SYNTAX	Gauge
	ACCESS	read-only
	STATUS	mandatory
	DESCRIPTION
		"The maximum byte rate for frames received by a port."
	::= { portStatusEntry 35 }

portMaxByteRateOut					OBJECT-TYPE
	SYNTAX	Gauge
	ACCESS	read-only
	STATUS	mandatory
	DESCRIPTION
		"The maximum byte rate for frames transmitted by a port."
	::= { portStatusEntry 36 }

portMaxQueueDepthIn					OBJECT-TYPE
	SYNTAX	Gauge
	ACCESS	read-only
	STATUS	mandatory
	DESCRIPTION
		"The maximum length of a port's receive queue." 
	::= { portStatusEntry 37 }

portMaxQueueDepthOut					OBJECT-TYPE
	SYNTAX	Gauge
	ACCESS	read-only
	STATUS	mandatory
	DESCRIPTION
		"The maximum length of a port's transmit queue." 
	::= { portStatusEntry 38 }

portBadFrames						OBJECT-TYPE
	SYNTAX	Counter
	ACCESS	read-only
	STATUS	mandatory
	DESCRIPTION
		"The number of frames dropped by the HDLC controller.
		 Examples of reasons why frames are dropped include
		 receiving a bad CRC and non-octet alignment."  
	::= { portStatusEntry 39 }
	
portShortFrames						OBJECT-TYPE
	SYNTAX	Counter
	ACCESS	read-only
	STATUS	mandatory
	DESCRIPTION
		"The number of frames received by the HDLC controller that
		 don't meet the minimum length restriction." 
	::= { portStatusEntry 40 }
	
portMissedFrames					OBJECT-TYPE
	SYNTAX	Counter
	ACCESS	read-only
	STATUS	mandatory
	DESCRIPTION
		"The number of receive frames missed by the HDLC
		 controller. This happens when the receiver's input queue
		 is full."  
	::= { portStatusEntry 41 }

portLongFrames						OBJECT-TYPE
	SYNTAX	Counter
	ACCESS	read-only
	STATUS	mandatory
	DESCRIPTION
		"The number of frames received longer than the maximum
		 length." 
	::= { portStatusEntry 42 }

portRxOverruns						OBJECT-TYPE
	SYNTAX	Counter
	ACCESS	read-only
	STATUS	mandatory
	DESCRIPTION
		"The number of receiver overruns the HDLC controller
		 experiences." 
	::= { portStatusEntry 43 }
	
portTxUnderruns						OBJECT-TYPE
	SYNTAX	Counter
	ACCESS	read-only
	STATUS	mandatory
	DESCRIPTION
		"The number of transmitter underruns the HDLC controller
		 experiences." 
	::= { portStatusEntry 44 }
	
portStatusEntryId					OBJECT-TYPE
	SYNTAX	INTEGER (0..7)
	ACCESS	read-only
	STATUS	mandatory
	DESCRIPTION
		"The port identifier (number) for this port."
	::= { portStatusEntry 45 }

portStatsClearedTime					OBJECT-TYPE
	SYNTAX	DisplayString
	ACCESS	read-only
	STATUS	mandatory
	DESCRIPTION
		"The amount of time since the last time the statistics
		 were cleared for this port." 
	::= { portStatusEntry 46 }

portDropBWadmitFrames					OBJECT-TYPE
	SYNTAX	Counter
	ACCESS	read-only
	STATUS	mandatory
	DESCRIPTION
		"The number of frames dropped due to Bandwidth Admission
		enforcement at the port.  This occurs when the number of
		frames is greater than (Bc + Be) during Tc over all Tc's 
		since the last clear of statistics.  In other words, these
		are the burst frames which exceed the sum of the Committed 
		Burst size (Bc) and the Excess Burst size (Be) over each 
		time interval (Tc).  This count is only valid when Bandwidth
		Admission is Enabled for the port; otherwise, it is zero." 
	::= { portStatusEntry 47 }

portDropInCongestFrames					OBJECT-TYPE
	SYNTAX	Counter
	ACCESS	read-only
	STATUS	mandatory
	DESCRIPTION
		"The number of frames dropped because the port input 
		buffer is fully congested." 
	::= { portStatusEntry 48 }

portDropOutCongestFrames				OBJECT-TYPE
	SYNTAX	Counter
	ACCESS	read-only
	STATUS	mandatory
	DESCRIPTION
		"The number of frames dropped because the port output
		buffer is fully congested."
	::= { portStatusEntry 49 }

portDropErroredFrames					OBJECT-TYPE
	SYNTAX	Counter
	ACCESS	read-only
	STATUS	mandatory
	DESCRIPTION
		"The number of frames dropped because of frame errors.
		These include: bad DLCI, invalid DLCI (with and without
		Cache), invalid source route frame, and wierd frame."
	::= { portStatusEntry 50 }

portDropPVCinactiveFrames				OBJECT-TYPE
	SYNTAX	Counter
	ACCESS	read-only
	STATUS	mandatory
	DESCRIPTION
		"The number of frames dropped because the PVC is inactive."
	::= { portStatusEntry 51 }

portDropPortDisabledFrames				OBJECT-TYPE
	SYNTAX	Counter
	ACCESS	read-only
	STATUS	mandatory
	DESCRIPTION
		"The number of frames dropped because the port is Disabled."
	::= { portStatusEntry 52 }


portChannelAssignment					OBJECT-TYPE
	SYNTAX	INTEGER
	ACCESS	read-only
	STATUS	mandatory
	DESCRIPTION
		"The DS0s assigned to this logical backcard port. These may, or may not,
		 be contiguous (when more than one is assigned)."
	::= { portStatusEntry 53 }

portAlarmedPVCs						OBJECT-TYPE
	SYNTAX  Gauge
	ACCESS  read-only
	STATUS  mandatory
	DESCRIPTION
		"The number of circuits on this port where all
		of the following conditions are true:
		- circuitState is not 'idle'
		- circuitStatus is not 'active'."
	::= { portStatusEntry 54 }

portSdlcEncapMapTable					OBJECT-TYPE
	SYNTAX 	SEQUENCE OF PortSdlcEncapMapEntry
	ACCESS	not-accessible
	STATUS	mandatory
	DESCRIPTION
		"The table containing address map translations between
		 DLCIs and SDLC/HDLC addresses. This table is applicable if
		 the portInterfaceProtocol is sdlcHdlcEncap and the
		 portSdlcEncapMode is addressMapped."   
	::= { port 3 }	

portSdlcEncapMapEntry					OBJECT-TYPE
	SYNTAX	PortSdlcEncapMapEntry
	ACCESS	not-accessible
	STATUS	mandatory
	DESCRIPTION
		"A row from the address map translation table."
	INDEX	{ addressMapPortNumber, addressMapSdlcAddress }
	::= { portSdlcEncapMapTable 1 }

PortSdlcEncapMapEntry		 ::= SEQUENCE {
		addressMapSdlcAddress				INTEGER (0..255),
		addressMapDlci					INTEGER (16..991),
		addressMapRowStatus				INTEGER,
		addressMapPortNumber				INTEGER (0..255)
	}

addressMapSdlcAddress					OBJECT-TYPE
	SYNTAX	INTEGER (0..255)
	ACCESS	read-write
	STATUS	mandatory
	DESCRIPTION
		"The SDLC or HDLC address that is mapped to a DLCI when
		 using SDLC/HDLC encapsulation." 
	::= { portSdlcEncapMapEntry 1 }

addressMapDlci						OBJECT-TYPE
	SYNTAX	INTEGER (16..991)
	ACCESS	read-write
	STATUS	mandatory
	DESCRIPTION
		"The DLCI used when mapping an SCLC/HDLC address when
		 SLDC/HDLC encapsulation is being used." 
	::= { portSdlcEncapMapEntry 2 }

addressMapRowStatus					OBJECT-TYPE
	SYNTAX	INTEGER {
		invalid(1),
		valid(2) 	
		}
	ACCESS	read-write
	STATUS	mandatory
	DESCRIPTION
		"Used to create a row in the table."
	::= { portSdlcEncapMapEntry 3 }

addressMapPortNumber					OBJECT-TYPE
	SYNTAX	INTEGER (0..255)
	ACCESS	read-only
	STATUS	mandatory
	DESCRIPTION
		"The port number index for the address map table."
	::= { portSdlcEncapMapEntry 4 }



circuitConfTable					OBJECT-TYPE
	SYNTAX	SEQUENCE OF CircuitConfEntry
	ACCESS	not-accessible
	STATUS	mandatory
	DESCRIPTION
		"A table containing configuration information for a
		 circuit. The objects in this table are always readable;
		 they can only be written (if accessible) only for the
		 instance in which the circuitConfPortNumber and
		 circuitConfDLCI correspond to the port number and DLCI at
		 the source (originate). When creating a new circuit, at a
		 minimum the destination address must be supplied. Note:
		 Before modifying any circuit configuration variables, the
		 circuit must be disabled (set circuitConfState =
		 'disable')."          
	::= { circuit 1 }

	
circuitConfEntry					OBJECT-TYPE
	SYNTAX	CircuitConfEntry
	ACCESS	not-accessible
	STATUS	mandatory
	DESCRIPTION
		"Configuration information about a particular circuit."
	INDEX	{ circuitConfPortNumber, circuitConfDLCI }
	::= { circuitConfTable 1 }

CircuitConfEntry ::= SEQUENCE {
		circuitSourceAddress				DisplayString (SIZE(0..16)),
		circuitSourceDLCI				INTEGER (0..1023),
		circuitDestinationAddress			DisplayString (SIZE(0..16)),
		circuitDestinationDLCI				INTEGER (0..1023),
		circuitUserSelectedPath				DisplayString (SIZE(0..256)),
		circuitAllowAlternatePath			INTEGER,
		circuitBandwidthAdmission			INTEGER,
		circuitCommittedInfoRate			INTEGER,
		circuitBurstSize				INTEGER,
		circuitExcessBurstSize				INTEGER,
		circuitPriority					INTEGER,
		circuitConfState				INTEGER,
		circuitConfPortNumber				INTEGER (0..255),
		circuitConfDLCI					INTEGER (0..1023)
	}

circuitSourceAddress						OBJECT-TYPE
	SYNTAX	DisplayString (SIZE(0..16))
	ACCESS	read-only
	STATUS	mandatory
	DESCRIPTION
		"The value of this object is the source (originate)
		 address of this circuit.  It is expressed in terms of
		 IDNX Node, Card, and Port (NxCyPz)."
	::= { circuitConfEntry 1 }
circuitSourceDLCI						OBJECT-TYPE
	SYNTAX	INTEGER (16..991)
	ACCESS	read-write
	STATUS	mandatory
	DESCRIPTION
		"The value of this object is the DLCI associated with the
		 source address of this circuit." 
	::= { circuitConfEntry 2 }

circuitDestinationAddress					OBJECT-TYPE
	SYNTAX	DisplayString (SIZE(0..16))
	ACCESS	read-write
	STATUS	mandatory
	DESCRIPTION
		"The value of this object is the destination (termination)
		 address of this circuit. The value must be consistent with
		 the endpoint of the user-selected path (if one exists). In
		 the case of a manager that can issue only single-varbind
		 Set requests, clear the user-selected path (if one exists)
		 before attempting to change this value."     
	::= { circuitConfEntry 3 }

circuitDestinationDLCI						OBJECT-TYPE
	SYNTAX	INTEGER (16..991)
	ACCESS	read-write
	STATUS	mandatory
	DESCRIPTION
		"The value of this object is the DLCI associated with the
		 destination address of this circuit." 
	::= { circuitConfEntry 4 }
	
circuitUserSelectedPath						OBJECT-TYPE
	SYNTAX	DisplayString (SIZE(0..256))
	ACCESS	read-write
	STATUS	mandatory
	DESCRIPTION
		"The value of this object is the required path through the
		 FRX network that this virtual circuit must take. The
		 endpoints of this path must be consistent with the
		 configured source and destination addresses. The value
		 'disabled' indicates that a user-selected path has not
		 been configured."      
	::= { circuitConfEntry 5 }

circuitAllowAlternatePath					OBJECT-TYPE
	SYNTAX	INTEGER {
		disabled(1),
		enabled(2)
		}
	ACCESS	read-write
	STATUS	mandatory
	DESCRIPTION
		"If a user-selected path has been configured, enabling
		 this variable allows the FRX to choose an alternate route
		 through the network if the user-selected path is
		 unavailable. Disabling it forces the FRX to wait until the
		 user-selected path is available before establishing the
		 PVC."    
	::= { circuitConfEntry 6 }

circuitBandwidthAdmission					OBJECT-TYPE
	SYNTAX	INTEGER {
		disabled(1),
		enabled(2)
		}
	ACCESS	read-write
	STATUS	mandatory
	DESCRIPTION
		"The field reflects the status of bandwidth admission for
		 this virtual circuit. If enabled then CIR, Be, and Bc must
		 be configured."  
	::= { circuitConfEntry 7 }

circuitCommittedInfoRate					OBJECT-TYPE
	SYNTAX	INTEGER
	ACCESS	read-write
	STATUS	mandatory
	DESCRIPTION
		"The committed information rate (in bits per second) for
		 this virtual circuit." 
	::= { circuitConfEntry 8 }

circuitBurstSize						OBJECT-TYPE
	SYNTAX	INTEGER
	ACCESS	read-write
	STATUS	mandatory
	DESCRIPTION
		"The burst size (Bc, expressed in bits) for this virtual
		 circuit." 
	::= { circuitConfEntry 9 }
	
circuitExcessBurstSize						OBJECT-TYPE
	SYNTAX	INTEGER
	ACCESS	read-write
	STATUS	mandatory
	DESCRIPTION
		"The excess burst size (Be, expressed in bits) for this
		 virtual circuit." 
	::= { circuitConfEntry 10 }

circuitPriority							OBJECT-TYPE
	SYNTAX	INTEGER {
		high(1),
		normal(2),
		low(3)
		}
	ACCESS	read-write
	STATUS	mandatory
	DESCRIPTION
		"The priority value of this circuit. If prioritized
		 circuits are not enabled on the port then the circuit
		 priority is normal. This parameter can not be set unless
		 Prioritize PVC is enabled for the port
		 (portPriorityQueueing)."   
	::= { circuitConfEntry 11 }

circuitConfState						OBJECT-TYPE
	SYNTAX	INTEGER {
		delete(1),
		install(2),
		disable(3),
		activate(4)
		}
	ACCESS	read-write
	STATUS	mandatory
	DESCRIPTION
		"The database state for this virtual circuit. Setting this
		 field to delete causes the virtual circuit to be deleted.
		 Setting this field to install either creates a new
		 circuit, or disables an already existing circuit.
		 Activating the circuit builds the circuit across the
		 network. Note: The database state must be set to 'disable'
		 before any other circuit parameters can be modified."     
		  
	::= { circuitConfEntry 12 }

circuitConfPortNumber						OBJECT-TYPE	
	SYNTAX	INTEGER (0..255)
	ACCESS	read-only
	STATUS	mandatory	
	DESCRIPTION
		"The first index into the circuit configuration table."
	::= { circuitConfEntry 13 }

circuitConfDLCI							OBJECT-TYPE	
	SYNTAX	INTEGER (0..1023)
	ACCESS	read-only
	STATUS	mandatory	
	DESCRIPTION
		"The second index into the circuit configuration table."
	::= { circuitConfEntry 14 }

circuitStatusTable						OBJECT-TYPE
	SYNTAX 	SEQUENCE OF CircuitStatusEntry
	ACCESS	not-accessible
	STATUS	mandatory
	DESCRIPTION
		"A table containing virtual circuit status for this port"
	::= { circuit 2 }

circuitStatusEntry						OBJECT-TYPE
	SYNTAX	CircuitStatusEntry
	ACCESS	not-accessible
	STATUS	mandatory
	DESCRIPTION
		"A status entry contains information about virtual
		 circuits." 
	INDEX 	{ circuitStatusPortNumber, circuitStatusDLCI }
	::= { circuitStatusTable 1 }

CircuitStatusEntry ::= SEQUENCE {
		circuitDataBaseState			INTEGER,
		circuitState				INTEGER,
		circuitSetupFailureReason		DisplayString,
		circuitLastDisconnectReason		DisplayString,
		circuitRoute				DisplayString (SIZE(0..256)),
		circuitWindowLength			INTEGER,
		circuitReceiveFrames			Counter,
		circuitTransmitFrames			Counter,
		circuitReceiveBytes			Counter,
		circuitTransmitBytes			Counter,
		circuitDroppedFrames			Counter,
		circuitMarkedDEFrames			Counter,
		circuitReceivedDEFrames			Counter,
		circuitCurrentTcBurstBits		Counter,
		circuitCurrentTcExcessBits		Counter,
		circuitMaximumBcBits			Counter,
		circuitMaximumBeBits			Counter,
		circuitAverageBc			Gauge,
		circuitAverageBe			Gauge,
		circuitStatus				INTEGER,
		circuitDownReason			DisplayString,
		circuitBECNReceiveFrames		Counter,
		circuitBECNTransmitFrames		Counter,
		circuitFECNReceiveFrames		Counter,
		circuitFECNTransmitFrames		Counter,
		circuitStatusPortNumber			INTEGER (0..255),
		circuitStatusDLCI			INTEGER (0..1023),
		circuitSrcSidePort			INTEGER,
		circuitSrcSideDLCI			INTEGER (0..1023),
		circuitDestSidePort			INTEGER,
		circuitDestSideDLCI			INTEGER (0..1023)
	}

circuitDataBaseState						OBJECT-TYPE
	SYNTAX	INTEGER {
		installed(1),
		active(2)
		}
	ACCESS	read-only
	STATUS	mandatory
	DESCRIPTION
		"The value of this object identifies the current database
		 state of the PVC." 
	::= { circuitStatusEntry 1 }

circuitState							OBJECT-TYPE
	SYNTAX	INTEGER {
		idle(1),
		setup(2),
		complete(3),
		disconnect(4)
		}
	ACCESS	read-only
	STATUS	mandatory
	DESCRIPTION
		"This field represents the status of the virtual circuit.
		 The possible values for the state are idle, setup,
		 complete, and disconnect."  
	::= { circuitStatusEntry 2 }

circuitSetupFailureReason					OBJECT-TYPE
	SYNTAX	DisplayString (SIZE(0..80))
	ACCESS	read-only
	STATUS	mandatory
	DESCRIPTION
		"This field is valid when the call cannot be completed.
		 The reason the circuit setup failed is contained in this
		 string."  
	::= { circuitStatusEntry 3 }

circuitLastDisconnectReason					OBJECT-TYPE
	SYNTAX	DisplayString (SIZE(0..80))
	ACCESS	read-only
	STATUS	mandatory
	DESCRIPTION
		"This field displays the reason for the last disconnect of
		 this virtual circuit, including normal termination." 
	::= { circuitStatusEntry 4 }

circuitRoute							OBJECT-TYPE
	SYNTAX	DisplayString (SIZE(0..256))
	ACCESS	read-only
	STATUS	mandatory
	DESCRIPTION
		"This field displays the route that the circuit has taken
		 through the FRX network.  It is expressed in terms of
		 IDNX Nodes and Cards (NxCy-NxCy-[...]NxCy.)"
	::= { circuitStatusEntry 5 }

circuitWindowLength						OBJECT-TYPE
	SYNTAX	INTEGER
	ACCESS	read-only
	STATUS	mandatory
	DESCRIPTION
		"The value of this object is the window length (Tc) used
		 for bandwidth admission procedures. The units are
		 tenths-of-seconds. This object is applicable only if
		 bandwidth admission is enabled for the circuit."   
	::= { circuitStatusEntry 6 }

circuitReceiveFrames						OBJECT-TYPE
	SYNTAX	Counter
	ACCESS	read-only
	STATUS	mandatory
	DESCRIPTION
		"The number of frames received by this circuit."
	::= { circuitStatusEntry 7 }

circuitTransmitFrames						OBJECT-TYPE
	SYNTAX	Counter
	ACCESS	read-only
	STATUS	mandatory
	DESCRIPTION
		"The number of frames transmitted by this circuit."
	::= { circuitStatusEntry 8 }

circuitReceiveBytes						OBJECT-TYPE
	SYNTAX	Counter
	ACCESS	read-only
	STATUS	mandatory
	DESCRIPTION
		"The number of bytes received by this circuit."
	::= { circuitStatusEntry 9 }

circuitTransmitBytes						OBJECT-TYPE
	SYNTAX	Counter
	ACCESS	read-only
	STATUS	mandatory
	DESCRIPTION
		"The number of bytes transmitted by this circuit."
	::= { circuitStatusEntry 10 }

circuitDroppedFrames						OBJECT-TYPE
	SYNTAX	Counter
	ACCESS	read-only
	STATUS	mandatory
	DESCRIPTION
		"This field represents the number of frames dropped for
		 this DLCI due to bandwidth admission procedures." 
	::= { circuitStatusEntry 11 }

circuitMarkedDEFrames						OBJECT-TYPE
	SYNTAX	Counter
	ACCESS	read-only
	STATUS	mandatory
	DESCRIPTION
		"This field represents the number of frames in which the
		 FRX set the DE bit, due to bandwidth admission
		 procedures." 
	::= { circuitStatusEntry 12 }

circuitReceivedDEFrames						OBJECT-TYPE
	SYNTAX	Counter
	ACCESS	read-only
	STATUS	mandatory
	DESCRIPTION
		"This field represents the number of frames received with
		 the DE bit set." 
	::= { circuitStatusEntry 13 }

circuitCurrentTcBurstBits					OBJECT-TYPE
	SYNTAX	Counter
	ACCESS	read-only
	STATUS	mandatory
	DESCRIPTION
		"The number of Bc bits received during the present Tc
		 window." 
	::= { circuitStatusEntry 14 }

circuitCurrentTcExcessBits					OBJECT-TYPE
	SYNTAX	Counter
	ACCESS	read-only
	STATUS	mandatory		
	DESCRIPTION
		"The number of Be bits received during the present Tc
		 window." 
	::= { circuitStatusEntry 15 }

circuitMaximumBcBits						OBJECT-TYPE
	SYNTAX	Counter
	ACCESS	read-only
	STATUS	mandatory
	DESCRIPTION
		"The maximum number of Bc bits received for this virtual
		 circuit." 
	::= { circuitStatusEntry 16 }

circuitMaximumBeBits						OBJECT-TYPE
	SYNTAX	Counter
	ACCESS	read-only
	STATUS	mandatory
	DESCRIPTION
		"The maximum number of Be bits received for this virtual
		 circuit." 
	::= { circuitStatusEntry 17 }

circuitAverageBc						OBJECT-TYPE
	SYNTAX	Gauge
	ACCESS	read-only
	STATUS	mandatory
	DESCRIPTION
		"The average number of Bc bits during the past five (5) Tc
		 periods." 
	::= { circuitStatusEntry 18 }

circuitAverageBe						OBJECT-TYPE
	SYNTAX	Gauge
	ACCESS	read-only
	STATUS	mandatory
	DESCRIPTION
		"The average number of Be bits during the past five (5) Tc
		 periods." 
	::= { circuitStatusEntry 19 }

circuitStatus							OBJECT-TYPE
	SYNTAX	INTEGER {
		inactive(1),
		active(2)
		}
	ACCESS	read-only
	STATUS	mandatory
	DESCRIPTION
		"The status of virtual circuit. The valid values are
		 Active or Inactive." 
	::= { circuitStatusEntry 20 }

circuitDownReason						OBJECT-TYPE
	SYNTAX	DisplayString (SIZE(0..80))
	ACCESS	read-only
	STATUS	mandatory
	DESCRIPTION
		"This field is a description of why the virtual circuit is
		 down." 
	::= { circuitStatusEntry 21 }

circuitBECNReceiveFrames					OBJECT-TYPE
	SYNTAX	Counter
	ACCESS	read-only
	STATUS	mandatory
	DESCRIPTION
		"The number of BECN frames received by the circuit."
	::= { circuitStatusEntry 22 }

circuitBECNTransmitFrames					OBJECT-TYPE
	SYNTAX	Counter
	ACCESS	read-only
	STATUS	mandatory
	DESCRIPTION
		"The number of BECN frames transmitted by the circuit."
	::= { circuitStatusEntry 23 }

circuitFECNReceiveFrames					OBJECT-TYPE
	SYNTAX	Counter
	ACCESS	read-only
	STATUS	mandatory
	DESCRIPTION
		"The number of FECN frames received by the circuit."
	::= { circuitStatusEntry 24 }

circuitFECNTransmitFrames					OBJECT-TYPE
	SYNTAX	Counter
	ACCESS	read-only
	STATUS	mandatory
	DESCRIPTION
		"The number of FECN frames transmitted by the circuit."
	::= { circuitStatusEntry 25 }

circuitStatusPortNumber						OBJECT-TYPE
	SYNTAX	INTEGER (0..255)
	ACCESS	read-only
	STATUS	mandatory
	DESCRIPTION
		"The first index into the circuit table."
	::= { circuitStatusEntry 26 }

circuitStatusDLCI						OBJECT-TYPE	
	SYNTAX	INTEGER (0..1023)
	ACCESS	read-only
	STATUS	mandatory
	DESCRIPTION
		"The second index into the circuit table."
	::= { circuitStatusEntry 27 }

circuitSrcSidePort						OBJECT-TYPE
	SYNTAX	INTEGER
	ACCESS	read-only
	STATUS	mandatory
	DESCRIPTION
		"A circuit segment within an FRX node has two endpoints,
		 each identified by a (port,DLCI) pair. This variable is
		 the source side port number. Note: A value of -1 means
		 'not applicable'. This variable is not applicable unless
		 the PVC state is Complete."      
	::= { circuitStatusEntry 28 }

circuitSrcSideDLCI						OBJECT-TYPE	
	SYNTAX	INTEGER (0..1023)
	ACCESS	read-only
	STATUS	mandatory
	DESCRIPTION
		"A circuit segment within an FRX node has two endpoints,
		 each identified by a (port,DLCI) pair. This variable is
		 the source side DLCI. Note: A value of -1 means 'not
		 applicable'. This variable is not applicable unless the
		 PVC state is Complete."      
	::= { circuitStatusEntry 29 }

circuitDestSidePort						OBJECT-TYPE
	SYNTAX	INTEGER
	ACCESS	read-only
	STATUS	mandatory
	DESCRIPTION
		"A circuit segment within an FRX node has two endpoints,
		 each identified by a (port,DLCI) pair. This variable is
		 the destination side port number. Note: A value of -1
		 means 'not applicable'. This variable is not applicable
		 unless the PVC state is Complete."      
	::= { circuitStatusEntry 30 }

circuitDestSideDLCI						OBJECT-TYPE	
	SYNTAX	INTEGER (0..1023)
	ACCESS	read-only
	STATUS	mandatory
	DESCRIPTION
		"A circuit segment within an FRX node has two endpoints,
		 each identified by a (port,DLCI) pair. This variable is
		 the destination side DLCI. Note: A value of -1 means 'not
		 applicable'. This variable is not applicable unless the
		 PVC state is Complete."      
	::= { circuitStatusEntry 31 }


operatorCount							OBJECT-TYPE
	SYNTAX	INTEGER
	ACCESS	read-only
	STATUS	mandatory
	DESCRIPTION
		"The number of operators currently installed on this FRX."
	::= { operator 1 }

operatorTable							OBJECT-TYPE
	SYNTAX	SEQUENCE OF OperatorTableEntry
	ACCESS	not-accessible
	STATUS	mandatory
	DESCRIPTION
		"The list of operators installed on this FRX. A row can be
		 added to this table using a set request that includes, at
		 minimum, a valid value for operatorIdentifier. A row can
		 be deleted by setting operatorRowStatus to invalid."   
	::= { operator 2 }

operatorTableEntry						OBJECT-TYPE
	SYNTAX	OperatorTableEntry
	ACCESS	not-accessible
	STATUS	mandatory
	DESCRIPTION
		"An entry (conceptual row) in the operator table."
	INDEX	{ operatorIndex }
	::= { operatorTable 1 }

OperatorTableEntry ::= SEQUENCE {
		operatorIndex			INTEGER (0..999),
		operatorIdentifier 		DisplayString,
		operatorPrivilege		INTEGER,
		operatorPassword		DisplayString,
		operatorRowStatus		INTEGER
	}

operatorIndex							OBJECT-TYPE
	SYNTAX	INTEGER (0..999)
	ACCESS  read-only
	STATUS	mandatory
	DESCRIPTION
		"The auxiliary variable used for identifying instances of
		 the columnar objects in the operator table." 
	::= { operatorTableEntry 1 }

operatorIdentifier						OBJECT-TYPE
	SYNTAX	DisplayString
	ACCESS  read-write
	STATUS	mandatory
	DESCRIPTION
		"A textual string giving the name of this operator. Cannot be empty. 
		A name for a new operator cannot duplicate a name for an existing operator.
	 	There is no default value, so a valid value for this column must be included
		in any set request for row creation."
	::= { operatorTableEntry 2 }

operatorPrivilege						OBJECT-TYPE
	SYNTAX	INTEGER {
		queryOnly(1),
		any(2)
		}
	ACCESS	read-write
	STATUS  mandatory
	DESCRIPTION
		"The privilege level for this operator."
	DEFVAL	{ queryOnly }
	::= { operatorTableEntry 3 }

operatorPassword						OBJECT-TYPE
	SYNTAX	DisplayString
	ACCESS	read-write
	STATUS	mandatory
	DESCRIPTION
		"The password for this operator. Can be empty."
	DEFVAL	{ ''h }		-- the empty string
	::= { operatorTableEntry 4 }

operatorRowStatus						OBJECT-TYPE
	SYNTAX	INTEGER {
		invalid(1),
		valid(2)
		}
	ACCESS	read-write
	STATUS	mandatory
	DESCRIPTION
		"Setting this column to invalid will delete this operator.
		 Setting it to valid has no effect."     
	DEFVAL	{ valid }
	::= { operatorTableEntry 5 }

-- The event group.
--
-- The FRX event type table, with one entry per type of FRX event.
-- Some field values can be set (trap enable/disable, forwarding
-- enable/disable), but the number of rows (corresponding to the
-- cardinality of the set of FRX events) cannot be changed by 
-- the manager.

eventTypeTable							OBJECT-TYPE
	SYNTAX		SEQUENCE OF EventTypeEntry
	ACCESS		not-accessible
	STATUS		mandatory
	DESCRIPTION	
		"A table listing the types of real-time events on the FRX.
		 The event types comprise two main categories:
		 configuration changes (PVC installed, port activated,
		 etc.), and status changes (port congested, node
		 decongested, etc.). Though the types of events are static,
		 some of their attributes, such as whether or not they
		 trigger an SNMP trap, are configurable."      
	::= { event 1 }

eventTypeEntry							OBJECT-TYPE
	SYNTAX		EventTypeEntry
	ACCESS		not-accessible
	STATUS		mandatory
	DESCRIPTION	
		"Information about a particular event on the FRX. The
		 event types comprise two main categories: configuration
		 changes (PVC installed, port activated, etc.), and status
		 changes (port congested, node decongested, etc.). Though
		 the types of events are static, some of their attributes,
		 such as whether or not they trigger an SNMP trap, are
		 configurable."      
	INDEX		{ eventTypeIndex }
	::= { eventTypeTable 1 }

EventTypeEntry ::= SEQUENCE {
		eventTypeIndex			INTEGER (0..99),
		eventTypeLevel			INTEGER,
		eventTypeDefaultLevel		INTEGER,
		eventTypeNetworkSignificant	INTEGER,
		eventTypeDefaultNetworkSignificant	INTEGER,
		eventTypeForward		INTEGER,
		eventTypeDefaultForward		INTEGER,
		eventTypeLog			INTEGER,
		eventTypeDefaultLog		INTEGER,
		eventTypeTrap			INTEGER,
		eventTypeDefaultTrap		INTEGER,
		eventTypeTrapNumber		INTEGER}

eventTypeIndex							OBJECT-TYPE
	SYNTAX		INTEGER (0..99)
	ACCESS		read-only
	STATUS		mandatory
	DESCRIPTION
		"Auxiliary variable used to identify row instances in the
		 eventTypeTable." 
	::= { eventTypeEntry 1 }

eventTypeLevel							OBJECT-TYPE
	SYNTAX		INTEGER {
			noAlarm(1), 
			fyiAlarm(2), 
			minorAlarm(3), 
			majorAlarm(4), 
			criticalAlarm(5)
			}
	ACCESS		read-write
	STATUS		mandatory
	DESCRIPTION
		"The IDNX alarm level of this FRX event; user
		 configurable." 
	::= { eventTypeEntry 2 }

eventTypeDefaultLevel						OBJECT-TYPE
	SYNTAX		INTEGER {
			noAlarm(1), 
			fyiAlarm(2), 
			minorAlarm(3), 
			majorAlarm(4), 
			criticalAlarm(5)
			}
	ACCESS		read-only
	STATUS		mandatory
	DESCRIPTION
		"The default IDNX alarm level of this FRX event."
	::= { eventTypeEntry 3 }

eventTypeNetworkSignificant					OBJECT-TYPE
	SYNTAX		INTEGER {
			false(1),
			true(2)
			}
	ACCESS		read-write
	STATUS		mandatory
	DESCRIPTION
		"Determines whether or not this type of event is forwarded
		 to the repository node for network-significant events." 
	::= { eventTypeEntry 4 }

eventTypeDefaultNetworkSignificant				OBJECT-TYPE
	SYNTAX		INTEGER {
			false(1),
			true(2)
			}
	ACCESS		read-only
	STATUS		mandatory
	DESCRIPTION
		"Default determination of whether or not this type of
		 event is forwarded to the repository node for
		 network-significant events."  
	::= { eventTypeEntry 5 }

eventTypeForward						OBJECT-TYPE
	SYNTAX		INTEGER {
			false(1),
			true(2)
			}
	ACCESS		read-write
	STATUS		mandatory
	DESCRIPTION
		"Determines whether or not this type of event is forwarded
		 to the IDNX  
event log; user configurable."
	::= { eventTypeEntry 6 }

eventTypeDefaultForward						OBJECT-TYPE
	SYNTAX		INTEGER {
			false(1),
			true(2)
			}
	ACCESS		read-only
	STATUS		mandatory
	DESCRIPTION
		"Default determination of whether or not this type of
		 event is forwarded to  
the IDNX event log."
	::= { eventTypeEntry 7 }

eventTypeLog							OBJECT-TYPE
	SYNTAX		INTEGER {
			false(1),
			true(2)
			}
	ACCESS		read-write
	STATUS		mandatory
	DESCRIPTION
		"Determines whether or not this type of event is logged to
		 the FRX (local) event log; user configurable." 
	::= { eventTypeEntry 8 }

eventTypeDefaultLog						OBJECT-TYPE
	SYNTAX		INTEGER {
			false(1),
			true(2)
			}
	ACCESS		read-only
	STATUS		mandatory
	DESCRIPTION
		"Default determination of whether or not this type of
		 event is logged to the FRX (local) event log." 
	::= { eventTypeEntry 9 }

eventTypeTrap							OBJECT-TYPE
	SYNTAX		INTEGER {
			false(1),
			true(2)
			}
	ACCESS		read-write
	STATUS		mandatory
	DESCRIPTION
		"Determines whether or not this type of event generates an
		 SNMP trap; user configurable." 
	::= { eventTypeEntry 10 }

eventTypeDefaultTrap						OBJECT-TYPE
	SYNTAX		INTEGER {
			false(1),
			true(2)
			}
	ACCESS		read-only
	STATUS		mandatory
	DESCRIPTION
		"Default determination of whether or not this type of
		 event generates an SNMP trap." 
	::= { eventTypeEntry 11 }

--
--
eventTypeTrapNumber						OBJECT-TYPE
	SYNTAX  INTEGER {
                        systemRestartTrap               (1),
                        systemSyserrTrap                (2),
                        configChangedTrap               (3),
                        nodeCongestedTrap               (4),
                        portInstalledTrap               (5),
                        portDeletedTrap                 (6),
                        portActivatedTrap               (7),
                        portDisabledTrap                (8),
                        portCongestedTrap               (9),
                        pvcInstalledTrap                (10),
                        pvcDeletedTrap                  (11),
                        pvcActivatedTrap                (12),
                        pvcDisabledTrap                 (13),
                        pvcStatusActiveTrap             (14),
                        pvcStatusInactiveTrap           (15),
                        cbusUpTrap                      (16),
                        cbusDownTrap                    (17),
                        serialFailTrap                  (18),
                        portUniActiveTrap               (19),
                        portUniInactiveTrap             (20),
                        portIDNXCallUpTrap              (21),
                        portIDNXCallDownTrap            (22),
                        nodeNotCongestedTrap            (23),
                        portNotCongestedTrap            (24),
                        operatorResetTrap               (25),
                        eventLogClearedTrap             (26),
                        configClearedTrap               (27),
                        functionMismatchTrap            (28),
                        eventLogErrorTrap               (29),
                        encapActiveTrap                 (30),
                        encapInactiveTrap               (31),
                        altPathUsedTrap                 (32),
                        pvcStateIdleTrap                (33),
                        pvcStateSetupTrap               (34),
                        pvcStateCompleteTrap            (35),
                        pvcStateDisconnectTrap          (36),
                        billingDownloadSuccessTrap      (37),
                        billingDownloadFailureTrap      (38),
                        billingDownloadThresholdTrap    (39),
                        configSyntaxErrorTrap           (40),
                        configDownloadSuccessTrap       (41),
                        configDownloadFailureTrap       (42),
                        nodeFlashMemErr                 (50),
                        nodeFlashWriteErr               (51),
                        nodeUserLogin                   (52),
                        nodeUserLogout                  (53),
                        dsx1NoAlarm                     (54),
                        dsx1RcvFarEndLOF                (55),
                        dsx1RcvFarEndLOFEnded           (56),
                        dsx1XmtFarEndLOF                (57),
                        dsx1XmtFarEndLOFEnding          (58),
                        dsx1RcvAIS                      (59),
                        dsx1RcvAISEnded                 (60),
                        dsx1XmtAIS                      (61),
                        dsx1XmtAISEnding                (62),
                        dsx1LossOfFrame                 (63),
                        dsx1LossOfFrameEnded            (64),
                        dsx1LossOfSignal                (65),
                        dsx1LossOfSignalEnded           (66),
                        dsx1LoopbackState               (67),
                        dsx1LoopbackStateEnded          (68),
                        dsx1T16AIS                      (69),
                        dsx1T16AISEnded                 (70),
                        dsx1RcvFarEndLOMF               (71),
                        dsx1RcvFarEndLOMFEnded          (72),
                        dsx1XmtFarEndLOMF               (73),
                        dsx1XmtFarEndLOMFEnding         (74),
                        dsx1RcvTestCode                 (75),
                        dsx1OtherFailure                (76),
                        nodeAlarmedPortsZero            (77),
                        portAlarmedPVCsZero             (78),
                        operatorInstallTrap             (79),
                        operatorDeleteTrap              (80)
                }
        ACCESS          read-only
        STATUS          mandatory
        DESCRIPTION
                "Enterprise-specific trap number associated with this
                 event." 
	     ::= { eventTypeEntry 12 }

-- do the network specific object here, basically the link state table 

networkNodeCount						OBJECT-TYPE
	SYNTAX	INTEGER (1..256)
	ACCESS	read-only
	STATUS	mandatory
	DESCRIPTION
		"The number of nodes this FRX knows about in the FRX
		 network." 
	::= { network 1 }

networkTable							OBJECT-TYPE
	SYNTAX	SEQUENCE OF NetworkTableEntry
	ACCESS	not-accessible
	STATUS	mandatory
	DESCRIPTION
		"The network table contains information on FRX nodes that
		 is known network wide. This information is distributed via
		 a link state algorithm."  
	::= { network 2 }

networkLinkStateTable 						OBJECT-TYPE
	SYNTAX	SEQUENCE OF NetworkLinkStateEntry
	ACCESS	not-accessible
	STATUS	mandatory
	DESCRIPTION
		"The link state table is a list of FRX nodes that are
		 neighbors to a given FRX node." 
	::= { network 3 }

networkTableEntry						OBJECT-TYPE
	SYNTAX	NetworkTableEntry
	ACCESS	not-accessible
	STATUS	mandatory
	DESCRIPTION
		"A row in the network table. Each row contains information
		 on a different node in the network." 
	INDEX 	{ networkTableIndex }
	::= { networkTable 1 }

NetworkTableEntry ::= SEQUENCE {
		networkNodeId				OCTET STRING,
		networkTableIndex			INTEGER (0..4294967295),
		networkNodeIpAddress			IpAddress,
		networkNodeNetMask			IpAddress
	}

networkNodeId							OBJECT-TYPE
	SYNTAX	OCTET STRING 
	ACCESS	read-only
	STATUS	mandatory
	DESCRIPTION
		"The IDNX domain-node-card address of the FRX node."
	::= { networkTableEntry 1 }

networkTableIndex						OBJECT-TYPE
	SYNTAX	INTEGER (0..4294967295)
	ACCESS	read-only
	STATUS	mandatory
	DESCRIPTION
		"The index for a particular row in the network table. The
		 value of this index is the FRX node number that
		 corresponds to the networkNodeId address."  
	::= { networkTableEntry 2 }

networkNodeIpAddress						OBJECT-TYPE
	SYNTAX	IpAddress
	ACCESS	read-only
	STATUS	mandatory
	DESCRIPTION
		"The IP address of the FRX node."
	::= { networkTableEntry 3 }

networkNodeNetMask						OBJECT-TYPE
	SYNTAX	IpAddress
	ACCESS	read-only
	STATUS	mandatory
	DESCRIPTION
		"The network mask of the FRX node."
	::= { networkTableEntry 4 }

networkLinkStateEntry						OBJECT-TYPE
	SYNTAX	NetworkLinkStateEntry
	ACCESS 	not-accessible
	STATUS	mandatory
	DESCRIPTION
		"A row in the link state table. Each row contains
		 information on the neighbor nodes for the FRX node in the
		 network table."  
	INDEX	{ linkStateNodeNumber, linkStateIndex }
	::= { networkLinkStateTable 1 }

NetworkLinkStateEntry ::= SEQUENCE {
		linkStateNeighborId				OCTET STRING,	
		linkStateNodeNumber				INTEGER (0..4294967295),
		linkStateIndex					INTEGER
	}

linkStateNeighborId						OBJECT-TYPE
	SYNTAX	OCTET STRING
	ACCESS	read-only
	STATUS	mandatory
	DESCRIPTION
		"The IDNX domain-node-card address of a neighbor FRX
		 node."
	::= { networkLinkStateEntry 1 }

linkStateNodeNumber						OBJECT-TYPE
	SYNTAX 	INTEGER (0..4294967295)
	ACCESS	read-only
	STATUS	mandatory
	DESCRIPTION
		"The first index into the link state table. The value of
		 this index is an FRX node number." 
	::= { networkLinkStateEntry 2 }

linkStateIndex							OBJECT-TYPE
	SYNTAX	INTEGER
	ACCESS	read-only
	STATUS	mandatory
	DESCRIPTION
		"The second index into the link state table."
	::= { networkLinkStateEntry 3 }

bufferCongestion 		OBJECT IDENTIFIER ::= { management 1 }

portCongestion	 		OBJECT IDENTIFIER ::= { management 2 }

routingParameters		OBJECT IDENTIFIER ::= { management 3 }

clearObjects			OBJECT IDENTIFIER ::= { management 4 }

saveConfiguration		OBJECT IDENTIFIER ::= { management 5 }

nmsDownloads			OBJECT IDENTIFIER ::= { management 6 }

bufferMinimumThreshold						OBJECT-TYPE
	SYNTAX	INTEGER (0..100)
	ACCESS	read-write
	STATUS	mandatory
	DESCRIPTION
		"The minimum percentage of buffer utilization to cause
		 node congestion." 
	::= { bufferCongestion 1 }

bufferDEFrameThreshold						OBJECT-TYPE
	SYNTAX	INTEGER (0..100)
	ACCESS	read-write
	STATUS	mandatory
	DESCRIPTION
		"The minimum percentage of buffer utilization that causes
		 DE frames to be dropped." 
	::= { bufferCongestion 2 }

bufferNormalFrameThreshold					OBJECT-TYPE
	SYNTAX	INTEGER(0..100)
	ACCESS	read-write
	STATUS	mandatory
	DESCRIPTION
		"The minimum percentage of buffer utilization that causes
		 normal data frames to be dropped." 
	::= { bufferCongestion 3 }

portCongestionTable						OBJECT-TYPE
	SYNTAX 	SEQUENCE OF PortCongestionEntry
	ACCESS	not-accessible
	STATUS	mandatory
	DESCRIPTION
		"A list of the port congestion parameters, row for each
		 port." 
	::= { portCongestion 1 }

portCongestionEntry						OBJECT-TYPE
	SYNTAX	PortCongestionEntry
	ACCESS	not-accessible
	STATUS	mandatory
	DESCRIPTION
		"A row from the port congestion parameters table."
	INDEX 	{ portCongId }
	::= { portCongestionTable 1 }

PortCongestionEntry ::= SEQUENCE {
		portCongId		 		INTEGER,
		portCongFrameDropRate			INTEGER,
		portCongUtilThreshold			INTEGER,
		portCongMinThreshold			INTEGER,
		portCongDEThreshold			INTEGER,
		portCongNormalThreshold			INTEGER
	}

portCongId							OBJECT-TYPE
	SYNTAX	INTEGER 
	ACCESS	read-only
	STATUS	mandatory
	DESCRIPTION
		"The port number associated with this row in the table."
	::= { portCongestionEntry 1 }

portCongFrameDropRate						OBJECT-TYPE
	SYNTAX	INTEGER	(1..10)
	ACCESS	read-write
	STATUS	mandatory
	DESCRIPTION
		"The rate at which normal frames are dropped during
		 extreme congestion." 
	DEFVAL	{ 4 }
	::= { portCongestionEntry 2 }

portCongUtilThreshold						OBJECT-TYPE
	SYNTAX	INTEGER (10..100)
	ACCESS	read-write
	STATUS	mandatory
	DESCRIPTION
		"The percentage of the port's access rate, at which time
		 congestion avoidance procedures are started." 
	DEFVAL	{ 90 }
	::= { portCongestionEntry 3 }

portCongMinThreshold						OBJECT-TYPE
	SYNTAX	INTEGER (1..10)
	ACCESS	read-write
	STATUS	mandatory
	DESCRIPTION
		"The number of seconds of port congestion before FECN and
		 BECN begin to get set." 
	DEFVAL	{ 3 }
	::= { portCongestionEntry 4 }

portCongDEThreshold						OBJECT-TYPE
	SYNTAX	INTEGER (1..10) 
	ACCESS	read-write
	STATUS	mandatory
	DESCRIPTION
		"The number of seconds of APPROACHINGCONGESTION before DE
		 frames begin to get dropped." 
	DEFVAL	{ 5 }
	::= { portCongestionEntry 5 }

portCongNormalThreshold						OBJECT-TYPE
	SYNTAX INTEGER (1..10)
	ACCESS	read-write
	STATUS	mandatory
	DESCRIPTION
		"The number of seconds of DECONGESTION before normal data
		 frames begin to get dropped." 
	DEFVAL	{ 7 }
	::= { portCongestionEntry 6 }

routingLongTimeout						OBJECT-TYPE
	SYNTAX	INTEGER (10..600)
	ACCESS	read-write
	STATUS	mandatory
	DESCRIPTION
		"The amount of time between normal routing table updates
		 for this FRX node." 
	::= { routingParameters 1 }

routingShortTimeout						OBJECT-TYPE
	SYNTAX	INTEGER (1..30)
	ACCESS	read-write
	STATUS	mandatory
	DESCRIPTION
		"The amount of time to wait after a PVC has been added or
		 deleted before distributing a new routing table update for
		 this FRX node."  
	::= { routingParameters 2 }

routingCriticalStaleness					OBJECT-TYPE
	SYNTAX	INTEGER (1..10)
	ACCESS	read-write
	STATUS	mandatory
	DESCRIPTION
		"The number of minor changes or short timeouts that causes
		 a routing table update to be distributed." 
	::= { routingParameters 3 }

clearEventLog			OBJECT IDENTIFIER ::= { clearObjects 1 }

clearPVCStats			OBJECT IDENTIFIER ::= { clearObjects 2 }

clearPortStats			OBJECT IDENTIFIER ::= { clearObjects 3 }

clearConfiguration		OBJECT IDENTIFIER ::= { clearObjects 4 }

eventLogClear							OBJECT-TYPE
	SYNTAX	INTEGER
	ACCESS	read-write		
	STATUS	mandatory
	DESCRIPTION
		"Writing to this object will cause the event log to be
		 cleared." 
	::= { clearEventLog 1 }

clearPVCStatsTable						OBJECT-TYPE
	SYNTAX 	SEQUENCE OF ClearPVCStatsEntry
	ACCESS	not-accessible
	STATUS	mandatory
	DESCRIPTION
		"A virtual table which is used to clear PVC statistics."
	::= { clearPVCStats 1 }

clearPVCStatsEntry						OBJECT-TYPE
	SYNTAX	ClearPVCStatsEntry
	ACCESS	not-accessible
	STATUS	mandatory
	DESCRIPTION
		"A row of parameters which are used to clear PVC based
		 statistics." 
	INDEX { clearPVCStatsPortId, clearPVCStatsPvcId }
	::= { clearPVCStatsTable 1 }

ClearPVCStatsEntry ::= SEQUENCE {
	clearPVCStatsPortId			INTEGER (0..7),
	clearPVCStatsPvcId			INTEGER (16..991),
	clearPVCStatsActivator			INTEGER
}

clearPVCStatsPortId						OBJECT-TYPE
	SYNTAX  INTEGER (0..7)
	ACCESS	read-only
	STATUS	mandatory
	DESCRIPTION
		"The port number identifying a PVC whose statistics are
		 to be cleared." 
	::= { clearPVCStatsEntry 1 }
	
clearPVCStatsPvcId						OBJECT-TYPE
	SYNTAX	INTEGER (16..991)
	ACCESS	read-only
	STATUS	mandatory
	DESCRIPTION
		"The DLCI value identifying a PVC whose statistics are to
		 be cleared." 
	::= { clearPVCStatsEntry 2 }

clearPVCStatsActivator						OBJECT-TYPE
	SYNTAX	INTEGER
	ACCESS	read-write
	STATUS	mandatory
	DESCRIPTION
		"After setting up the clearPVCStatsPVCId and
		 clearPVCStatsPortId fields, writing to this field will
		 clear the identified PVCs counters."  
	::= { clearPVCStatsEntry 3 }

clearPortStatsTable						OBJECT-TYPE
	SYNTAX	SEQUENCE OF ClearPortStatsEntry
	ACCESS	not-accessible
	STATUS	mandatory
	DESCRIPTION
		"A virtual table for clearing port based statistics."
	::= { clearPortStats 1 }

clearPortStatsEntry						OBJECT-TYPE
	SYNTAX	ClearPortStatsEntry
	ACCESS	not-accessible
	STATUS	mandatory
	DESCRIPTION
		"A virtual entry used to clear port statistics."
	INDEX { clearPortStatsPortId }
	::= { clearPortStatsTable 1 }

ClearPortStatsEntry ::= SEQUENCE {
	clearPortStatsPortId			INTEGER,
	clearPortStatsActivator			INTEGER
	}
	
clearPortStatsPortId						OBJECT-TYPE
	SYNTAX	INTEGER 
	ACCESS	read-write
	STATUS	mandatory
	DESCRIPTION
		"Setting the field to a valid port number and then writing
		 to clearPortStatsActivator will clear a port's
		 statistics."  
	::= { clearPortStatsEntry 1 }

clearPortStatsActivator						OBJECT-TYPE
	SYNTAX	INTEGER
	ACCESS	read-write
	STATUS	mandatory
	DESCRIPTION
		"After setting the clearPortStatsPortId field with a valid
		 port number, writing to this field will clear a port's
		 statistics."  
	::= { clearPortStatsEntry 2 }

configurationClear						OBJECT-TYPE
	SYNTAX	INTEGER
	ACCESS	read-write
	STATUS	mandatory
	DESCRIPTION
		"Writing anything to this field will clear a FRX node's
		 configuration. This can be very dangerous." 
	::= { clearConfiguration 1 }

configurationSave						OBJECT-TYPE
	SYNTAX	INTEGER
	ACCESS	read-write
	STATUS	mandatory
	DESCRIPTION
		"Writing anything to this field will cause the current
		 configuration to be saved in the non-volatile store of the
		 PX card."  
	::= { saveConfiguration		 1 }

fullConfigDownload						OBJECT-TYPE
	SYNTAX	INTEGER
	ACCESS	read-write
	STATUS	mandatory	
	DESCRIPTION
		"Writing anything to this field will cause the current PVC
		 configuration to be downloaded to a NMS workstation." 
	::= { nmsDownloads 1 }


gwIPAddress							OBJECT-TYPE
	SYNTAX	IpAddress
	ACCESS	read-write
	STATUS	mandatory
	DESCRIPTION
		"The IP Address of the FRX backcard."
	::= { gateway 1 }

gwNetMask							OBJECT-TYPE
	SYNTAX	IpAddress
	ACCESS	read-write
	STATUS	mandatory
	DESCRIPTION
		"The network mask of the FRX backcard."
	::= { gateway 2 }

gwRARP								OBJECT-TYPE
	SYNTAX	INTEGER{
		disabled(1),
		enabled(2)
		}
	ACCESS	read-only
	STATUS	deprecated
	DESCRIPTION
		"This parameter is not supported. A get on this OID will
		 return disabled. A set on this OID will have no effect." 
	::= { gateway 3 }

gwRIP								OBJECT-TYPE
	SYNTAX	INTEGER{
		disabled(1),
		enabled(2)
		}
	ACCESS	read-write
	STATUS	mandatory
	DESCRIPTION
		"Enable or disable the use of RIP (Routing Information
		 Protocol). With RIP disabled, the user must install static
		 routes on the attached workstation. Default state is
		 disabled."   
	::= { gateway 4 }

gwIPAccessTable							OBJECT-TYPE
	SYNTAX		SEQUENCE OF GwIPAccessEntry
	ACCESS		not-accessible
	STATUS		mandatory
	DESCRIPTION	
		"A table of IP host or network addresses whose managers
		 are allowed to access the FRX gateway." 
	::= { gateway 5 }

gwIPAccessEntry							OBJECT-TYPE
	SYNTAX		GwIPAccessEntry
	ACCESS		not-accessible
	STATUS		mandatory
	DESCRIPTION	
		"An IP host or network addresses whose managers are
		 allowed to access the FRX gateway." 
	INDEX		{ gwIPAccessAddress }
	::= { gwIPAccessTable 1 }

GwIPAccessEntry ::= SEQUENCE {
		gwIPAccessRowStatus			INTEGER,
		gwIPAccessAddress       		IpAddress }

gwIPAccessRowStatus						OBJECT-TYPE
	SYNTAX	INTEGER {
		invalid(1),
		valid(2)
		}
	ACCESS		read-write
	STATUS		mandatory
	DESCRIPTION
		"Auxiliary variable used to create or delete row instances
		 in the gateway's IP address access table."  
	::= { gwIPAccessEntry 1 }

gwIPAccessAddress						OBJECT-TYPE
	SYNTAX		IpAddress
	ACCESS		read-write
	STATUS		mandatory
	DESCRIPTION
		"The IP address of a host or network that is allowed to
		 access the FRX gateway." 
	::= { gwIPAccessEntry 2 }


--
-- the DS1/E1 transmission variables
--


-- The DS1 Near End Group

-- Implementation of this group is mandatory for all systems
-- that attach to a DS1 Interface.

-- The DS1 Near End Group consists of four tables:
--    DS1 Configuration
--    DS1 Current
--    DS1 Interval
--    DS1 Total

-- the DS1 Configuration Table
--
-- dsx1ConfigTable 						OBJECT-TYPE
--	 SYNTAX  SEQUENCE OF Dsx1ConfigEntry
--	 ACCESS  not-accessible
--	 STATUS  mandatory
--	 DESCRIPTION
--		"The DS1 Configuration table."
--	::= { dsx 1 }
--
-- dsx1ConfigEntry					OBJECT-TYPE
--	 SYNTAX  Dsx1ConfigEntry
--	 ACCESS  not-accessible
--	 STATUS  mandatory
--	 DESCRIPTION
--		"An entry in the DS1 Configuration table."
--	 INDEX   { dsx1LineIndex }
--	::= { dsx1ConfigTable 1 }

 dsx1ConfigEntry 	OBJECT IDENTIFIER	::= { dsx 1 }

--Dsx1ConfigEntry ::=
-- SEQUENCE {
--	 dsx1LineIndex                                INTEGER,
--	 dsx1IfIndex                                  INTEGER,
--	 dsx1TimeElapsed                              INTEGER,
--	 dsx1ValidIntervals                           INTEGER,
--	 dsx1LineType                                 INTEGER,
--	 dsx1LineCoding                               INTEGER,
--	 dsx1SendCode                                 INTEGER,
--	 dsx1CircuitIdentifier                        DisplayString,
--	 dsx1LoopbackConfig                           INTEGER,
--	 dsx1LineStatus                               INTEGER,
--	 dsx1LineMode                                 INTEGER,
--	 dsx1TransmitClockSource                      INTEGER,
--	 dsx1Fdl                                      INTEGER,
--	 dsx1YellowAlarmStyle                         INTEGER
-- }
--
--
-- dsx1LineIndex 				OBJECT-TYPE
--	 SYNTAX  INTEGER (1..'7fffffff'h)
--	 ACCESS  read-only
--	 STATUS  mandatory
--	 DESCRIPTION
--		"This object is the identifier of a DS1  Inter-
--		face on a managed device.  If there is an ifEn-
--		try that is directly associated with  this  and
--		only  this  DS1  interface,  it should have the
--		same value as ifIndex.   Otherwise,  the  value
--		exceeds  ifNumber,  and  is a unique identifier
--		following this rule: inside  interfaces  (e.g.,
--		equipment  side)  with even numbers and outside
--		interfaces  (e.g,  network   side)   with   odd
--		numbers."
--	::= { dsx1ConfigEntry 1 }
--
--
-- dsx1IfIndex 				OBJECT-TYPE
--	 SYNTAX  INTEGER (1..'7fffffff'h)
--	 ACCESS  read-only
--	 STATUS  mandatory
--	 DESCRIPTION
--		"This value for this object  is  equal  to  the
--		value  of  ifIndex from the Interfaces table of
--		MIB II (RFC 1213)."
--	::= { dsx1ConfigEntry 2 }
--

 dsx1Initialized 				OBJECT-TYPE
	 SYNTAX  INTEGER (0..1)
	 ACCESS  not-accessible
	 STATUS  mandatory
	 DESCRIPTION
		"Used to pad the wan structure in wan.h; it is
		not used for SNMP."
	::= { dsx1ConfigEntry 1 }

 dsx1TimeElapsed 				OBJECT-TYPE
	 SYNTAX  INTEGER (0..899)
	 ACCESS  read-only
	 STATUS  mandatory
	 DESCRIPTION
		"The number of seconds that have elapsed  since
		the  beginning of the current error-measurement
		period."
	::= { dsx1ConfigEntry 2 }


 dsx1ValidIntervals 						OBJECT-TYPE
	 SYNTAX  INTEGER (0..96)
	 ACCESS  read-only
	 STATUS  mandatory
	 DESCRIPTION
		"The number of  previous  intervals  for  which
		valid data was collected.  The value will be 96
		unless the interface was brought on-line within
		the last 24 hours, in which case the value will
		be the number of complete 15  minute  intervals
		the since interface has been online."
	::= { dsx1ConfigEntry 3 }


 dsx1LineType 							OBJECT-TYPE
	 SYNTAX  INTEGER {
				 other(1),
				 dsx1ESF(2),
				 dsx1D4(3),
				 dsx1E1(4),
				 dsx1E1-CRC(5),
				 dsx1E1-MF(6),
				 dsx1E1-CRC-MF(7)
			 }
	 ACCESS  read-write
	 STATUS  mandatory
	 DESCRIPTION
		"This variable indicates  the  variety  of  DS1
		Line  implementing  this  circuit.  The type of
		circuit affects the number of bits  per  second
		that  the circuit can reasonably carry, as well
		as the interpretation of the  usage  and  error
		statistics.  The values, in sequence, describe:

		TITLE:        SPECIFICATION:
		dsx1ESF       Extended SuperFrame DS1
		dsx1D4        AT&T D4 format DS1
		dsx1E1        CCITT Recommendation G.704
						(Table 4a)
		dsx1E1-CRC    CCITT Recommendation G.704
						(Table 4b)
		dsxE1-MF      G.704 (Table 4a) with TS16
						multiframing enabled
		dsx1E1-CRC-MF G.704 (Table 4b) with TS16
						multiframing enabled"

	::= { dsx1ConfigEntry 4 }


--
-- (EYA) Took out JBZS (as per GHW), since it
--	 is covered by AMI. (8/2/95)
--
--		dsx1JBZS refers the Jammed  Bit  Zero  Suppres-
--		sion,  in  which  the  AT&T specification of at
--		least one pulse every 8 bit periods is literal-
--		ly  implemented  by forcing a pulse in bit 8 of
--		each channel.  Thus, only seven bits per  chan-
--		nel, or 1.344 Mbps, is available for data.
--
 dsx1LineCoding 						OBJECT-TYPE
	 SYNTAX  INTEGER {
				 dsx1B8ZS (1),
				 dsx1HDB3 (2),
				 dsx1ZBTSI (3),
				 dsx1AMI (4),
				 other(5)
			 }
	 ACCESS  read-write
	 STATUS  mandatory
	 DESCRIPTION
		"This variable describes the  variety  of  Zero
		Code  Suppression  used  on  the link, which in
		turn affects a number of its characteristics.

		dsx1B8ZS refers to the use of a specified  pat-
		tern  of  normal  bits  and  bipolar violations
		which are used to replace a sequence  of  eight
		zero bits.

		ANSI Clear Channels may use dsx1ZBTSI, or  Zero
		Byte Time Slot Interchange.

		E1 links, with or without CRC, use dsx1HDB3  or
		dsx1AMI.

		dsx1AMI refers to a mode wherein no  zero  code
		suppression  is  present  and the line encoding
		does not solve the problem directly.   In  this
		application, the higher layer must provide data
		which meets or exceeds the  pulse  density  re-
		quirements, such as inverting HDLC data."
	::= { dsx1ConfigEntry 5 }


 dsx1SendCode 							OBJECT-TYPE
	 SYNTAX  INTEGER {
				 dsx1SendNoCode(1),
				 dsx1SendLineCode(2),
				 dsx1SendPayloadCode(3),
				 dsx1SendResetCode(4),
				 dsx1SendQRS(5),
				 dsx1Send511Pattern(6),
				 dsx1Send3in24Pattern(7),
				 dsx1SendOtherTestPattern(8)
			 }
	 ACCESS  read-write
	 STATUS  mandatory
	 DESCRIPTION
		"This variable indicates what type of  code  is
		being sent across the DS1 interface by the dev-
		ice.  The values mean:

		dsx1SendNoCode
			 sending looped or normal data

		dsx1SendLineCode
			 sending a request for a line loopback

		dsx1SendPayloadCode
			 sending a request for a payload loopback

		dsx1SendResetCode
			 sending a loopback termination request

		dsx1SendQRS
			 sending a Quasi-Random Signal  (QRS)  test
			 pattern

		dsx1Send511Pattern
			 sending a 511 bit fixed test pattern

		dsx1Send3in24Pattern
			 sending a fixed test pattern of 3 bits set
			 in 24

		dsx1SendOtherTestPattern
			 sending a test pattern  other  than  those
			 described by this object"
	::= { dsx1ConfigEntry 6 }


 dsx1CircuitIdentifier 						OBJECT-TYPE
	 SYNTAX  DisplayString (SIZE (0..255))
	 ACCESS  read-write
	 STATUS  mandatory
	 DESCRIPTION
		"This  variable   contains   the   transmission
		vendor's circuit identifier, for the purpose of
		facilitating troubleshooting."
	::= { dsx1ConfigEntry 7 }


 dsx1LoopbackConfig 						OBJECT-TYPE
	 SYNTAX  INTEGER {
				 dsx1NoLoop(1),
				 dsx1PayloadLoop(2),
				 dsx1LineLoop(3),
				 dsx1OtherLoop(4)
			 }
	 ACCESS  read-write
	 STATUS  mandatory
	 DESCRIPTION
		"This variable represents the  loopback  confi-
		guration of the DS1 interface.  Agents support-
		ing read/write access should return badValue in
		response to a requested loopback state that the
		interface does not support.  The values mean:

		dsx1NoLoop
			 Not in the loopback state.  A device  that
			 is not capable of performing a loopback on
			 the interface shall always return this  as
			 it's value.

		dsx1PayloadLoop
			 The received signal at this  interface  is
			 looped  through  the device. Typically the
			 received signal is  looped  back  for  re-
			 transmission  after  it has passed through
			 the device's framing function.

		dsx1LineLoop
			 The received signal at this interface does
			 not  go  through the device (minimum pene-
			 tration) but is looped back out.

		dsx1OtherLoop
			 Loopbacks that are not defined here."
	::= { dsx1ConfigEntry 8 }


 dsx1LineStatus 						OBJECT-TYPE
	 SYNTAX  INTEGER (1..8191)
	 ACCESS  read-only
	 STATUS  mandatory
	 DESCRIPTION
		"This variable indicates the Line Status of the
		interface.   It contains loopback, failure, re-
		ceived 'alarm'  and transmitted 'alarm'  infor-
		mation.

-- The dsx1LineStatus is a bit  map  represented  as  a  sum,
-- therefore, it can represent multiple failures (alarms) and
-- a LoopbackState simultaneously.

-- dsx1NoAlarm should be set if and only if no other flag  is
-- set.

-- If the dsx1LoopbackState bit is set, the loopback  in  ef-
-- fect can be determined from the dsx1LoopbackConfig object.

-- The various bit positions are:
--   1      dsx1NoAlarm             No Alarm Present
--   2      dsx1RcvFarEndLOF        Far end LOF (a.k.a. Yellow Alarm)
--   4      dsx1XmtFarEndLOF        Near end sending LOF Indication
--   8      dsx1RcvAIS              Far end sending AIS
--  16      dsx1XmtAIS              Near end sending AIS
--  32      dsx1LossOfFrame         Near end LOF (a.k.a. Red Alarm)
--  64      dsx1LossOfSignal        Near end Loss Of Signal
-- 128      dsx1LoopbackState       Near end is looped
-- 256      dsx1T16AIS              E1 TS16 AIS
-- 512      dsx1RcvFarEndLOMF       Far End Sending TS16 LOMF
-- 1024     dsx1XmtFarEndLOMF       Near End Sending TS16 LOMF
-- 2048     dsx1RcvTestCode         Near End detects a test code
-- 4096     dsx1OtherFailure        any line status not defined here"
	::= { dsx1ConfigEntry 9 }




 dsx1LineMode 						OBJECT-TYPE
	 SYNTAX  INTEGER {
				dsx1Mode0dB(1),
				dsx1Mode75dB(2),
				dsx1Mode15dB(3),
				dsx1Mode225dB(4),
				dsx1Mode133ft(5),
				dsx1Mode266ft(6),
				dsx1Mode399ft(7),
				dsx1Mode533ft(8),
				dsx1Mode655ft(9),
				dsx1Mode120Ohm(10),
				dsx1Mode75Ohm(11)
			 }
	 ACCESS  read-write
	 STATUS  mandatory
	 DESCRIPTION
		"This set of values describes the mode of the WAN I/F.
		 For DS1 lines it sets the mode to CSU by way of a
		 standard dB level, and for DSX configurations sets the
		 line buildout in feet.
       for E1 lines, it sets the mode in Ohm"
	::= { dsx1ConfigEntry 10 }


 dsx1TransmitClockSource 					OBJECT-TYPE
	 SYNTAX  INTEGER {
				 loopTiming (1),
				 localTiming (2),
				 throughTiming (3)
			 }
	 ACCESS  read-write
	 STATUS  mandatory
	 DESCRIPTION
		"The source of Tranmit Clock.

		 'loopTiming' indicates that the recovered  re-
		ceive clock is used as the transmit clock.

		 'localTiming' indicates  that  a  local  clock
		source is used.

		 'throughTiming' indicates that  recovered  re-
		ceive  clock  from another interface is ised as
		the transmit clock."
	::= { dsx1ConfigEntry 11 }


 dsx1Fdl 							OBJECT-TYPE
	 SYNTAX  INTEGER {
				   other(1),
				   dsx1Ansi-T1-403(2),
				   dsx1Att-54016(4),
				   dsx1Ansi-T1-403-Att-54016(6),
				   dsx1Fdl-none(8)
			 }
	 ACCESS  read-write
	 STATUS  mandatory
	 DESCRIPTION
		"This bitmap describes the use of  the  facili-
		ties data link, and is the sum of the capabili-
		ties:

		 'other' indicates that a protocol  other  than
		one following is used.

		 'dsx1Ansi-T1-403' refers to the  FDL  exchange
		recommended by ANSI.  (This is a T1-only option.)

		 'dsx1Att-54016' refers to ESF FDL exchanges.
		(This is a T1-only option.)

		 'dsx1Fdl-none' indicates that the device  does
		not use the FDL."
	::= { dsx1ConfigEntry 12 }


dsx1YellowAlarmStyle						OBJECT-TYPE
	 SYNTAX  INTEGER {
				   usaYellowAlarms(1),
				   japaneseYellowAlarms(2)
			 }
	 ACCESS  read-write
	 STATUS  mandatory
	 DESCRIPTION
		"This variable describes the use of  the  yellow
		alarm style when in D4 line encoding mode."
	::= { dsx1ConfigEntry 13 }



-- the DS1 Current Table
--
-- The DS1 current table contains various statistics being
-- collected for the current 15 minute interval.
--
 dsx1CurrentTable 						OBJECT-TYPE
	 SYNTAX  SEQUENCE OF Dsx1CurrentEntry
	 ACCESS  not-accessible
	 STATUS  mandatory
	 DESCRIPTION
		"The DS1 Current table."
	::= { dsx 2 }

 dsx1CurrentEntry 						OBJECT-TYPE
	 SYNTAX  Dsx1CurrentEntry
	 ACCESS  not-accessible
	 STATUS  mandatory
	 DESCRIPTION
		"An entry in the DS1 Current table."
	INDEX   { dsx1CurrentIndex }
	::= { dsx1CurrentTable 1 }

 Dsx1CurrentEntry ::=
  SEQUENCE {
 	 dsx1CurrentIndex                INTEGER,
 	 dsx1CurrentESs                  Gauge,
 	 dsx1CurrentSESs                 Gauge,
 	 dsx1CurrentSEFSs                Gauge,
 	 dsx1CurrentUASs                 Gauge,
 	 dsx1CurrentCSSs                 Gauge,
 	 dsx1CurrentPCVs                 Gauge,
 	 dsx1CurrentLESs                 Gauge,
 	 dsx1CurrentBESs                 Gauge,
 	 dsx1CurrentDMs                  Gauge,
 	 dsx1CurrentLCVs                 Gauge
  }

 dsx1CurrentIndex 						OBJECT-TYPE
	 SYNTAX  INTEGER (1..'7fffffff'h)
	 ACCESS  read-only
	 STATUS  mandatory
	 DESCRIPTION
		"The index value which uniquely identifies  the
		DS1  interface  to which this entry is applica-
		ble.  The interface identified by a  particular
		value  of  this  index is the same interface as
		identified by the same value as a dsx1LineIndex
		object instance."
	 ::= { dsx1CurrentEntry 1 }


 dsx1CurrentESs 						OBJECT-TYPE
	 SYNTAX  Gauge
	 ACCESS  read-only
	 STATUS  mandatory
	 DESCRIPTION
		"The number of Errored Seconds, encountered  by
		a DS1 interface in the current 15 minute inter-
		val."
	 ::= { dsx1CurrentEntry 2 }


 dsx1CurrentSESs 						OBJECT-TYPE
	 SYNTAX  Gauge
	 ACCESS  read-only
	 STATUS  mandatory
	 DESCRIPTION
		"The number of Severely Errored Seconds encoun-
		tered  by  a  DS1  interface  in the current 15
		minute interval."
	 ::= { dsx1CurrentEntry 3 }


 dsx1CurrentSEFSs 						OBJECT-TYPE
	 SYNTAX  Gauge
	 ACCESS  read-only
	 STATUS  mandatory
	 DESCRIPTION
		"The number of Severely Errored Framing Seconds
		encountered  by  a DS1 interface in the current
		15 minute interval."
	 ::= { dsx1CurrentEntry 4 }


 dsx1CurrentUASs 						OBJECT-TYPE
	 SYNTAX  Gauge
	 ACCESS  read-only
	 STATUS  mandatory
	 DESCRIPTION
		"The number of Unavailable Seconds  encountered
		by a DS1 interface in the current 15 minute in-
		terval."
	 ::= { dsx1CurrentEntry 5 }


 dsx1CurrentCSSs 						OBJECT-TYPE
	 SYNTAX  Gauge
	 ACCESS  read-only
	 STATUS  mandatory
	 DESCRIPTION
		"The number of Controlled Slip Seconds  encoun-
		tered  by  a  DS1  interface  in the current 15
		minute interval."
	 ::= { dsx1CurrentEntry 6 }


 dsx1CurrentPCVs 						OBJECT-TYPE
	 SYNTAX  Gauge
	 ACCESS  read-only
	 STATUS  mandatory
	 DESCRIPTION
		"The number of Path Coding  Violations  encoun-
		tered  by  a  DS1  interface  in the current 15
		minute interval."
	 ::= { dsx1CurrentEntry 7 }


 dsx1CurrentLESs 						OBJECT-TYPE
	 SYNTAX  Gauge
	 ACCESS  read-only
	 STATUS  mandatory
	 DESCRIPTION
		"The number of Line Errored Seconds encountered
		by a DS1 interface in the current 15 minute in-
		terval."
	 ::= { dsx1CurrentEntry 8 }


 dsx1CurrentBESs 						OBJECT-TYPE
	 SYNTAX Gauge
	 ACCESS read-only
	 STATUS mandatory
	 DESCRIPTION
		"The number of Bursty  Errored  Seconds  (BESs)
		encountered  by  a DS1 interface in the current
		15 minute interval."
	 ::= { dsx1CurrentEntry 9 }


 dsx1CurrentDMs 						OBJECT-TYPE
	 SYNTAX Gauge
	 ACCESS read-only
	 STATUS mandatory
	 DESCRIPTION
		"The number of Degraded Minutes  (DMs)  encoun-
		tered  by  a  DS1  interface  in the current 15
		minute interval."
	 ::= { dsx1CurrentEntry 10 }


 dsx1CurrentLCVs 						OBJECT-TYPE
	 SYNTAX Gauge
	 ACCESS read-only
	 STATUS mandatory
	 DESCRIPTION
		"The number of Line Code Violations (LCVs)  en-
		countered  by a DS1 interface in the current 15
		minute interval."
	 ::= {dsx1CurrentEntry 11 }


-- the DS1 Interval
--
-- The DS1 Interval Table contains various statistics
-- collected by each DS1 Interface over the previous 24 hours of
-- operation.  The past 24 hours are broken into 96 completed
-- 15 minute intervals.
--
 dsx1IntervalTable 						OBJECT-TYPE
	 SYNTAX  SEQUENCE OF Dsx1IntervalEntry
	 ACCESS  not-accessible
	 STATUS  mandatory
	 DESCRIPTION
		"The DS1 Interval table."
	::= { dsx 3 }

 dsx1IntervalEntry 						OBJECT-TYPE
	 SYNTAX  Dsx1IntervalEntry
	 ACCESS  not-accessible
	 STATUS  mandatory
	 DESCRIPTION
		"An entry in the DS1 Interval table."
	INDEX   { dsx1IntervalIndex, dsx1IntervalNumber }
	::= { dsx1IntervalTable 1 }

 Dsx1IntervalEntry ::=
  SEQUENCE {
 	 dsx1IntervalIndex                  INTEGER,
 	 dsx1IntervalNumber                 INTEGER,
 	 dsx1IntervalESs                    Gauge,
 	 dsx1IntervalSESs                   Gauge,
 	 dsx1IntervalSEFSs                  Gauge,
 	 dsx1IntervalUASs                   Gauge,
 	 dsx1IntervalCSSs                   Gauge,
 	 dsx1IntervalPCVs                   Gauge,
 	 dsx1IntervalLESs                   Gauge,
 	 dsx1IntervalBESs                   Gauge,
 	 dsx1IntervalDMs                    Gauge,
 	 dsx1IntervalLCVs                   Gauge
  }

 dsx1IntervalIndex 						OBJECT-TYPE
	 SYNTAX  INTEGER (1..'7fffffff'h)
	 ACCESS  read-only
	 STATUS  mandatory
	 DESCRIPTION
		"The index value which uniquely identifies  the
		DS1  interface  to which this entry is applica-
		ble.  The interface identified by a  particular
		value  of  this  index is the same interface as
		identified by the same value as a dsx1LineIndex
		object instance."
	 ::= { dsx1IntervalEntry 1 }


 dsx1IntervalNumber 						OBJECT-TYPE
	 SYNTAX  INTEGER (1..96)
	 ACCESS  read-only
	 STATUS  mandatory
	 DESCRIPTION
		"A number between 1 and 96, where 1 is the most
		recently completed 15 minute interval and 96 is
		the least recently completed 15 minutes  inter-
		val   (assuming   that  all  96  intervals  are
		valid)."
	 ::= { dsx1IntervalEntry 2 }


 dsx1IntervalESs 						OBJECT-TYPE
	 SYNTAX  Gauge
	 ACCESS  read-only
	 STATUS  mandatory
	 DESCRIPTION
		"The number of Errored Seconds encountered by a
		DS1  interface in one of the previous 96, indi-
		vidual 15 minute, intervals."
	 ::= { dsx1IntervalEntry 3 }


 dsx1IntervalSESs 						OBJECT-TYPE
	 SYNTAX  Gauge
	 ACCESS  read-only
	 STATUS  mandatory
	 DESCRIPTION
		"The number of Severely Errored Seconds encoun-
		tered by a DS1 interface in one of the previous
		96, individual 15 minute, intervals."
	 ::= { dsx1IntervalEntry 4 }


 dsx1IntervalSEFSs 						OBJECT-TYPE
	 SYNTAX  Gauge
	 ACCESS  read-only
	 STATUS  mandatory
	 DESCRIPTION
		"The number of Severely Errored Framing Seconds
		encountered  by  a  DS1 interface in one of the
		previous 96, individual 15 minute, intervals."
	 ::= { dsx1IntervalEntry 5 }


 dsx1IntervalUASs 						OBJECT-TYPE
	 SYNTAX  Gauge
	 ACCESS  read-only
	 STATUS  mandatory
	 DESCRIPTION
		"The number of Unavailable Seconds  encountered
		by  a  DS1 interface in one of the previous 96,
		individual 15 minute, intervals."
	 ::= { dsx1IntervalEntry 6 }


 dsx1IntervalCSSs 						OBJECT-TYPE
	 SYNTAX  Gauge
	 ACCESS  read-only
	 STATUS  mandatory
	 DESCRIPTION
		"The number of Controlled Slip Seconds  encoun-
		tered by a DS1 interface in one of the previous
		96, individual 15 minute, intervals."
	 ::= { dsx1IntervalEntry 7 }

 dsx1IntervalPCVs 						OBJECT-TYPE
	 SYNTAX  Gauge
	 ACCESS  read-only
	 STATUS  mandatory
	 DESCRIPTION
		"The number of Path Coding  Violations  encoun-
		tered by a DS1 interface in one of the previous
		96, individual 15 minute, intervals."
	 ::= { dsx1IntervalEntry 8 }


 dsx1IntervalLESs 						OBJECT-TYPE
	 SYNTAX  Gauge
	 ACCESS  read-only
	 STATUS  mandatory
	 DESCRIPTION
		"The number of Line Errored Seconds encountered
		by  a  DS1 interface in one of the previous 96,
		individual 15 minute, intervals."
	 ::= { dsx1IntervalEntry 9 }


 dsx1IntervalBESs 						OBJECT-TYPE
	 SYNTAX Gauge
	 ACCESS read-only
	 STATUS mandatory
	 DESCRIPTION
		"The number of Bursty  Errored  Seconds  (BESs)
		encountered  by  a  DS1 interface in one of the
		previous 96, individual 15 minute, intervals."
	 ::= { dsx1IntervalEntry 10 }


 dsx1IntervalDMs 						OBJECT-TYPE
	 SYNTAX Gauge
	 ACCESS read-only
	 STATUS mandatory
	 DESCRIPTION
		"The number of Degraded Minutes  (DMs)  encoun-
		tered by a DS1 interface in one of the previous
		96, individual 15 minute, intervals."
	 ::= { dsx1IntervalEntry 11 }


 dsx1IntervalLCVs 						OBJECT-TYPE
	 SYNTAX Gauge
	 ACCESS read-only
	 STATUS mandatory
	 DESCRIPTION
		"The number of Line Code Violations (LCVs)  en-
		countered  by a DS1 interface in the current 15
		minute interval."
	 ::= { dsx1IntervalEntry 12 }


-- the DS1 Total
--
-- The DS1 Total Table contains the cumulative sum of the
-- various statistics for the 24 hour period preceding the
-- current interval.
--
 dsx1TotalTable 						OBJECT-TYPE
	 SYNTAX  SEQUENCE OF Dsx1TotalEntry
	 ACCESS  not-accessible
	 STATUS  mandatory
	 DESCRIPTION
		"The DS1 Total table.  24 hour interval."
	::= { dsx 4 }


 dsx1TotalEntry 						OBJECT-TYPE
	 SYNTAX  Dsx1TotalEntry
	 ACCESS  not-accessible
	 STATUS  mandatory
	 DESCRIPTION
		"An entry in the DS1 Total table."
	INDEX   { dsx1TotalIndex }
	::= { dsx1TotalTable 1 }

Dsx1TotalEntry ::=
 SEQUENCE {
	 dsx1TotalIndex                      INTEGER,
	 dsx1TotalESs                        Gauge,
	 dsx1TotalSESs                       Gauge,
	 dsx1TotalSEFSs                      Gauge,
	 dsx1TotalUASs                       Gauge,
	 dsx1TotalCSSs                       Gauge,
	 dsx1TotalPCVs                       Gauge,
	 dsx1TotalLESs                       Gauge,
	 dsx1TotalBESs                       Gauge,
	 dsx1TotalDMs                        Gauge,
	 dsx1TotalLCVs                       Gauge
 }

 dsx1TotalIndex 						OBJECT-TYPE
	 SYNTAX  INTEGER (1..'7fffffff'h)
	 ACCESS  read-only
	 STATUS  mandatory
	 DESCRIPTION
		"The index value which uniquely identifies  the
		DS1  interface  to which this entry is applica-
		ble.  The interface identified by a  particular
		value  of  this  index is the same interface as
		identified by the same value as a dsx1LineIndex
		object instance."
	 ::= { dsx1TotalEntry 1 }


 dsx1TotalESs 							OBJECT-TYPE
	 SYNTAX  Gauge
	 ACCESS  read-only
	 STATUS  mandatory
	 DESCRIPTION
		"The number of Errored Seconds encountered by a
		DS1 interface in the previous 24 hour interval"
	 ::= { dsx1TotalEntry 2 }


 dsx1TotalSESs 							OBJECT-TYPE
	 SYNTAX  Gauge
	 ACCESS  read-only
	 STATUS  mandatory
	 DESCRIPTION
		"The number of Severely Errored Seconds encoun-
		tered  by  a  DS1  interface in the previous 24
		hour interval."
	 ::= { dsx1TotalEntry 3 }


 dsx1TotalSEFSs 						OBJECT-TYPE
	 SYNTAX  Gauge
	 ACCESS  read-only
	 STATUS  mandatory
	 DESCRIPTION
		"The number of Severely Errored Framing Seconds
		encountered  by a DS1 interface in the previous
		24 hour interval."
	 ::= { dsx1TotalEntry 4 }


 dsx1TotalUASs 							OBJECT-TYPE
	 SYNTAX  Gauge
	 ACCESS  read-only
	 STATUS  mandatory
	 DESCRIPTION
		"The number of Unavailable Seconds  encountered
		by  a DS1 interface in the previous 24 hour in-
		terval."
	 ::= { dsx1TotalEntry 5 }


 dsx1TotalCSSs 							OBJECT-TYPE
	 SYNTAX  Gauge
	 ACCESS  read-only
	 STATUS  mandatory
	 DESCRIPTION
		"The number of Controlled Slip Seconds  encoun-
		tered  by  a  DS1  interface in the previous 24
		hour interval."
	 ::= { dsx1TotalEntry 6 }


 dsx1TotalPCVs 							OBJECT-TYPE
	 SYNTAX  Gauge
	 ACCESS  read-only
	 STATUS  mandatory
	 DESCRIPTION
		"The number of Path Coding  Violations  encoun-
		tered  by  a  DS1  interface in the previous 24
		hour interval."
	 ::= { dsx1TotalEntry 7 }


 dsx1TotalLESs 							OBJECT-TYPE
	 SYNTAX  Gauge
	 ACCESS  read-only
	 STATUS  mandatory
	 DESCRIPTION
		"The number of Line Errored Seconds encountered
		by  a DS1 interface in the previous 24 hour in-
		terval."
	 ::= { dsx1TotalEntry 8 }


 dsx1TotalBESs 							OBJECT-TYPE
	 SYNTAX Gauge
	 ACCESS read-only
	 STATUS mandatory
	 DESCRIPTION
		"The number of Bursty  Errored  Seconds  (BESs)
		encountered  by a DS1 interface in the previous
		24 hour interval."
	 ::= { dsx1TotalEntry 9 }


 dsx1TotalDMs 							OBJECT-TYPE
	 SYNTAX Gauge
	 ACCESS read-only
	 STATUS mandatory
	 DESCRIPTION
		"The number of Degraded Minutes  (DMs)  encoun-
		tered  by  a  DS1  interface in the previous 24
		hour interval."
	 ::= { dsx1TotalEntry 10 }


 dsx1TotalLCVs 							OBJECT-TYPE
	 SYNTAX Gauge
	 ACCESS read-only
	 STATUS mandatory
	 DESCRIPTION
		"The number of Line Code Violations (LCVs)  en-
		countered  by a DS1 interface in the current 15
		minute interval."
	 ::= { dsx1TotalEntry 11 }


-- The DS1 Far End Group

-- Implementation of this group is optional for all systems
-- that attach to a DS1 Interface.

-- The DS1 Far End Group consists of three tables:
--   DS1 Far End Current
--   DS1 Far End Interval
--   DS1 Far End Total

-- The DS1 Far End Current Table

-- The DS1 Far End Current table contains various statistics being
-- collected for the current 15 minute interval.
-- The statistics are collected from the far end messages on the
-- Facilities Data Link.  The definitions are the same as described for
-- the near-end information.
--
 dsx1FarEndCurrentTable 					OBJECT-TYPE
	 SYNTAX  SEQUENCE OF Dsx1FarEndCurrentEntry
	 ACCESS  not-accessible
	 STATUS  mandatory
	 DESCRIPTION
		"The DS1 Far End Current table."
	::= { dsx 5 }


 dsx1FarEndCurrentEntry 					OBJECT-TYPE
	 SYNTAX  Dsx1FarEndCurrentEntry
	 ACCESS  not-accessible
	 STATUS  mandatory
	 DESCRIPTION
		"An entry in the DS1 Far End Current table."
	INDEX   { dsx1FarEndCurrentIndex }
	::= { dsx1FarEndCurrentTable 1 }

Dsx1FarEndCurrentEntry ::=
 SEQUENCE {
	 dsx1FarEndCurrentIndex                  INTEGER,
	 dsx1FarEndTimeElapsed                   INTEGER,
	 dsx1FarEndValidIntervals                INTEGER,
	 dsx1FarEndCurrentESs                    Gauge,
	 dsx1FarEndCurrentSESs                   Gauge,
	 dsx1FarEndCurrentSEFSs                  Gauge,
	 dsx1FarEndCurrentUASs                   Gauge,
	 dsx1FarEndCurrentCSSs                   Gauge,
	 dsx1FarEndCurrentLESs                   Gauge,
	 dsx1FarEndCurrentPCVs                   Gauge,
	 dsx1FarEndCurrentBESs                   Gauge,
	 dsx1FarEndCurrentDMs                    Gauge
 }

 dsx1FarEndCurrentIndex 					OBJECT-TYPE
	 SYNTAX  INTEGER (1..'7fffffff'h)
	 ACCESS  read-only
	 STATUS  mandatory
	 DESCRIPTION
		"The index value which uniquely identifies  the
		DS1  interface  to which this entry is applica-
		ble.  The interface identified by a  particular
		value  of  this  index is the same interface as
		identified by the same value  an  dsx1LineIndex
		object instance."
	 ::= { dsx1FarEndCurrentEntry 1 }


 dsx1FarEndTimeElapsed 						OBJECT-TYPE
	 SYNTAX  INTEGER (0..899)
	 ACCESS  read-only
	 STATUS  mandatory
	 DESCRIPTION
			 "The number of seconds that  have  elapsed
			 since the beginning of the far end current
			 error-measurement period."
	 ::= { dsx1FarEndCurrentEntry 2 }

 dsx1FarEndValidIntervals 					OBJECT-TYPE
	 SYNTAX  INTEGER (0..96)
	 ACCESS  read-only
	 STATUS  mandatory
	 DESCRIPTION
			 "The number of previous far end  intervals
			 for  which  valid data was collected.  The
			 value will be 96 unless the interface  was
			 brought  online  within the last 24 hours,
			 in which case the value will be the number
			 of  complete  15  minute far end intervals
			 since the interface has been online."
	 ::= { dsx1FarEndCurrentEntry 3 }


 dsx1FarEndCurrentESs 						OBJECT-TYPE
	 SYNTAX  Gauge
	 ACCESS  read-only
	 STATUS  mandatory
	 DESCRIPTION
		"The number of Far Far End Errored Seconds  en-
		countered  by a DS1 interface in the current 15
		minute interval."
	 ::= { dsx1FarEndCurrentEntry 4 }


 dsx1FarEndCurrentSESs 						OBJECT-TYPE
	 SYNTAX  Gauge
	 ACCESS  read-only
	 STATUS  mandatory
	 DESCRIPTION
		"The number of Far End Severely Errored Seconds
		encountered  by  a DS1 interface in the current
		15 minute interval."
	 ::= { dsx1FarEndCurrentEntry 5 }


 dsx1FarEndCurrentSEFSs 					OBJECT-TYPE
	 SYNTAX  Gauge
	 ACCESS  read-only
	 STATUS  mandatory
	 DESCRIPTION
		"The number of Far End Severely Errored Framing
		Seconds  encountered  by a DS1 interface in the
		current 15 minute interval."
	 ::= { dsx1FarEndCurrentEntry 6 }


 dsx1FarEndCurrentUASs 						OBJECT-TYPE
	 SYNTAX  Gauge
	 ACCESS  read-only
	 STATUS  mandatory
	 DESCRIPTION
		"The number of Unavailable Seconds  encountered
		by a DS1 interface in the current 15 minute in-
		terval."
	 ::= { dsx1FarEndCurrentEntry 7 }


 dsx1FarEndCurrentCSSs 						OBJECT-TYPE
	 SYNTAX  Gauge
	 ACCESS  read-only
	 STATUS  mandatory
	 DESCRIPTION
		"The number of Far End Controlled Slip  Seconds
		encountered  by  a DS1 interface in the current
		15 minute interval."
	 ::= { dsx1FarEndCurrentEntry 8 }


 dsx1FarEndCurrentLESs 						OBJECT-TYPE
	 SYNTAX  Gauge
	 ACCESS  read-only
	 STATUS  mandatory
	 DESCRIPTION
		"The number of Far End Line Errored Seconds en-
		countered  by a DS1 interface in the current 15
		minute interval."
	 ::= { dsx1FarEndCurrentEntry 9 }


 dsx1FarEndCurrentPCVs 						OBJECT-TYPE
	 SYNTAX  Gauge
	 ACCESS  read-only
	 STATUS  mandatory
	 DESCRIPTION
		"The number of Far End Path  Coding  Violations
		reported  via the far end block error count en-
		countered by a DS1 interface in the current  15
		minute interval."
	 ::= { dsx1FarEndCurrentEntry 10 }


 dsx1FarEndCurrentBESs 						OBJECT-TYPE
	 SYNTAX Gauge
	 ACCESS read-only
	 STATUS mandatory
	 DESCRIPTION
		"The number of Bursty  Errored  Seconds  (BESs)
		encountered  by  a DS1 interface in the current
		15 minute interval."
	 ::= { dsx1FarEndCurrentEntry 11 }


 dsx1FarEndCurrentDMs 						OBJECT-TYPE
	 SYNTAX Gauge
	 ACCESS read-only
	 STATUS mandatory
	 DESCRIPTION
		"The number of Degraded Minutes  (DMs)  encoun-
		tered  by  a  DS1  interface  in the current 15
		minute interval."
	 ::= { dsx1FarEndCurrentEntry 12 }


-- The DS1 Far End Interval Table

-- The DS1 Far End Interval Table contains various statistics
-- collected by each DS1 interface over the previous 24 hours of
-- operation.  The past 24 hours are broken into 96
-- completed 15 minute intervals.
--
 dsx1FarEndIntervalTable 					OBJECT-TYPE
	 SYNTAX  SEQUENCE OF Dsx1FarEndIntervalEntry
	 ACCESS  not-accessible
	 STATUS  mandatory
	 DESCRIPTION
		"The DS1 Far End Interval table."
	 ::= { dsx 6 }


 dsx1FarEndIntervalEntry 					OBJECT-TYPE
	 SYNTAX  Dsx1FarEndIntervalEntry
	 ACCESS  not-accessible
	 STATUS  mandatory
	 DESCRIPTION
		"An entry in the DS1 Far End Interval table."
	INDEX   { dsx1FarEndIntervalIndex, dsx1FarEndIntervalNumber }
	::= { dsx1FarEndIntervalTable 1 }

Dsx1FarEndIntervalEntry ::=
 SEQUENCE {
	 dsx1FarEndIntervalIndex			INTEGER,
	 dsx1FarEndIntervalNumber			INTEGER,
	 dsx1FarEndIntervalESs				Gauge,
	 dsx1FarEndIntervalSESs				Gauge,
	 dsx1FarEndIntervalSEFSs			Gauge,
	 dsx1FarEndIntervalUASs				Gauge,
	 dsx1FarEndIntervalCSSs				Gauge,
	 dsx1FarEndIntervalLESs				Gauge,
	 dsx1FarEndIntervalPCVs				Gauge,
	 dsx1FarEndIntervalBESs				Gauge,
	 dsx1FarEndIntervalDMs				Gauge
 }

 dsx1FarEndIntervalIndex 				OBJECT-TYPE
	 SYNTAX  INTEGER (1..'7fffffff'h)
	 ACCESS  read-only
	 STATUS  mandatory
	 DESCRIPTION
		"The index value which uniquely identifies  the
		DS1  interface  to which this entry is applica-
		ble.  The interface identified by a  particular
		value  of  this  index is the same interface as
		identified by the same value as a dsx1LineIndex
		object instance."
	 ::= { dsx1FarEndIntervalEntry 1 }


 dsx1FarEndIntervalNumber 				OBJECT-TYPE
	 SYNTAX  INTEGER (1..96)
	 ACCESS  read-only
	 STATUS  mandatory
	 DESCRIPTION
		"A number between 1 and 96, where 1 is the most
		recently completed 15 minute interval and 96 is
		the least recently completed 15 minutes  inter-
		val   (assuming   that  all  96  intervals  are
		valid)."
	 ::= { dsx1FarEndIntervalEntry 2 }


 dsx1FarEndIntervalESs 					OBJECT-TYPE
	 SYNTAX  Gauge
	 ACCESS  read-only
	 STATUS  mandatory
	 DESCRIPTION
		"The number of Far End Errored Seconds  encoun-
		tered by a DS1 interface in one of the previous
		96, individual 15 minute, intervals."
	 ::= { dsx1FarEndIntervalEntry 3 }


 dsx1FarEndIntervalSESs 				OBJECT-TYPE
	 SYNTAX  Gauge
	 ACCESS  read-only
	 STATUS  mandatory
	 DESCRIPTION
		"The number of Far End Severely Errored Seconds
		encountered  by  a  DS1 interface in one of the
		previous 96, individual 15 minute, intervals."
	 ::= { dsx1FarEndIntervalEntry 4 }


 dsx1FarEndIntervalSEFSs 				OBJECT-TYPE
	 SYNTAX  Gauge
	 ACCESS  read-only
	 STATUS  mandatory
	 DESCRIPTION
		"The number of Far End Severely Errored Framing
		Seconds  encountered  by a DS1 interface in one
		of the previous 96, individual 15  minute,  in-
		tervals."
	 ::= { dsx1FarEndIntervalEntry 5 }


 dsx1FarEndIntervalUASs 				OBJECT-TYPE
	 SYNTAX  Gauge
	 ACCESS  read-only
	 STATUS  mandatory
	 DESCRIPTION
		"The number of Unavailable Seconds  encountered
		by  a  DS1 interface in one of the previous 96,
		individual 15 minute, intervals."
	 ::= { dsx1FarEndIntervalEntry 6 }


 dsx1FarEndIntervalCSSs 				OBJECT-TYPE
	 SYNTAX  Gauge
	 ACCESS  read-only
	 STATUS  mandatory
	 DESCRIPTION
		"The number of Far End Controlled Slip  Seconds
		encountered  by  a  DS1 interface in one of the
		previous 96, individual 15 minute, intervals."
	 ::= { dsx1FarEndIntervalEntry 7 }


 dsx1FarEndIntervalLESs 				OBJECT-TYPE
	 SYNTAX  Gauge
	 ACCESS  read-only
	 STATUS  mandatory
	 DESCRIPTION
		"The number of Far End Line Errored Seconds en-
		countered by a DS1 interface in one of the pre-
		vious 96, individual 15 minute, intervals."
	 ::= { dsx1FarEndIntervalEntry 8 }


 dsx1FarEndIntervalPCVs 				OBJECT-TYPE
	 SYNTAX  Gauge
	 ACCESS  read-only
	 STATUS  mandatory
	 DESCRIPTION
		"The number of Far End Path  Coding  Violations
		reported  via the far end block error count en-
		countered by a DS1 interface in one of the pre-
		vious 96, individual 15 minute, intervals."
	 ::= { dsx1FarEndIntervalEntry 9 }


 dsx1FarEndIntervalBESs 				OBJECT-TYPE
	 SYNTAX Gauge
	 ACCESS read-only
	 STATUS mandatory
	 DESCRIPTION
		"The number of Bursty  Errored  Seconds  (BESs)
		encountered  by  a  DS1 interface in one of the
		previous 96, individual 15 minute, intervals."
	 ::= { dsx1FarEndIntervalEntry 10 }


 dsx1FarEndIntervalDMs 					OBJECT-TYPE
	 SYNTAX Gauge
	 ACCESS read-only
	 STATUS mandatory
	 DESCRIPTION
		"The number of Degraded Minutes  (DMs)  encoun-
		tered by a DS1 interface in one of the previous
		96, individual 15 minute, intervals."
	 ::= { dsx1FarEndIntervalEntry 11 }


-- The DS1 Far End Total Table

-- The DS1 Far End Total Table contains the cumulative sum of the
-- various statistics for the 24 hour period preceding the
-- current interval.
--
 dsx1FarEndTotalTable 				OBJECT-TYPE
	 SYNTAX  SEQUENCE OF Dsx1FarEndTotalEntry
	 ACCESS  not-accessible
	 STATUS  mandatory
	 DESCRIPTION
		"The DS1 Far End Total table."
	 ::= { dsx 7 }


 dsx1FarEndTotalEntry 				OBJECT-TYPE
	 SYNTAX  Dsx1FarEndTotalEntry
	 ACCESS  not-accessible
	 STATUS  mandatory
	 DESCRIPTION
		"An entry in the DS1 Far End Total table."
	INDEX   { dsx1FarEndTotalIndex }
	::= { dsx1FarEndTotalTable 1 }

Dsx1FarEndTotalEntry ::=
 SEQUENCE {
	 dsx1FarEndTotalIndex				INTEGER,
	 dsx1FarEndTotalESs				Gauge,
	 dsx1FarEndTotalSESs				Gauge,
	 dsx1FarEndTotalSEFSs				Gauge,
	 dsx1FarEndTotalUASs				Gauge,
	 dsx1FarEndTotalCSSs				Gauge,
	 dsx1FarEndTotalLESs				Gauge,
	 dsx1FarEndTotalPCVs				Gauge,
	 dsx1FarEndTotalBESs				Gauge,
	 dsx1FarEndTotalDMs				Gauge
 }

 dsx1FarEndTotalIndex 				OBJECT-TYPE
	 SYNTAX  INTEGER (1..'7fffffff'h)
	 ACCESS  read-only
	 STATUS  mandatory
	 DESCRIPTION
		"The index value which uniquely identifies  the
		DS1  interface  to which this entry is applica-
		ble.  The interface identified by a  particular
		value  of  this  index is the same interface as
		identified by the same value  an  dsx1LineIndex
		object instance."
	 ::= { dsx1FarEndTotalEntry 1 }


 dsx1FarEndTotalESs 					OBJECT-TYPE
	 SYNTAX  Gauge
	 ACCESS  read-only
	 STATUS  mandatory
	 DESCRIPTION
		"The number of Far End Errored Seconds  encoun-
		tered  by  a  DS1  interface in the previous 24
		hour interval."
	 ::= { dsx1FarEndTotalEntry 2 }


 dsx1FarEndTotalSESs 					OBJECT-TYPE
	 SYNTAX  Gauge
	 ACCESS  read-only
	 STATUS  mandatory
	 DESCRIPTION
		"The number of Far End Severely Errored Seconds
		encountered  by a DS1 interface in the previous
		24 hour interval."
	 ::= { dsx1FarEndTotalEntry 3 }


 dsx1FarEndTotalSEFSs 					OBJECT-TYPE
	 SYNTAX  Gauge
	 ACCESS  read-only
	 STATUS  mandatory
	 DESCRIPTION
		"The number of Far End Severely Errored Framing
		Seconds  encountered  by a DS1 interface in the
		previous 24 hour interval."
	 ::= { dsx1FarEndTotalEntry 4 }


 dsx1FarEndTotalUASs 					OBJECT-TYPE
	 SYNTAX  Gauge
	 ACCESS  read-only
	 STATUS  mandatory
	 DESCRIPTION
		"The number of Unavailable Seconds  encountered
		by  a DS1 interface in the previous 24 hour in-
		terval."
	 ::= { dsx1FarEndTotalEntry 5 }


 dsx1FarEndTotalCSSs 					OBJECT-TYPE
	 SYNTAX  Gauge
	 ACCESS  read-only
	 STATUS  mandatory
	 DESCRIPTION
		"The number of Far End Controlled Slip  Seconds
		encountered  by a DS1 interface in the previous
		24 hour interval."
	 ::= { dsx1FarEndTotalEntry 6 }


 dsx1FarEndTotalLESs 					OBJECT-TYPE
	 SYNTAX  Gauge
	 ACCESS  read-only
	 STATUS  mandatory
	 DESCRIPTION
		"The number of Far End Line Errored Seconds en-
		countered by a DS1 interface in the previous 24
		hour interval."
	 ::= { dsx1FarEndTotalEntry 7 }


 dsx1FarEndTotalPCVs 					OBJECT-TYPE
	 SYNTAX  Gauge
	 ACCESS  read-only
	 STATUS  mandatory
	 DESCRIPTION
		"The number of Far End Path  Coding  Violations
		reported  via the far end block error count en-
		countered by a DS1 interface in the previous 24
		hour interval."
	 ::= { dsx1FarEndTotalEntry 8 }


 dsx1FarEndTotalBESs 					OBJECT-TYPE
	 SYNTAX Gauge
	 ACCESS read-only
	 STATUS mandatory
	 DESCRIPTION
		"The number of Bursty  Errored  Seconds  (BESs)
		encountered  by a DS1 interface in the previous
		24 hour interval."
	 ::= { dsx1FarEndTotalEntry 9 }


 dsx1FarEndTotalDMs 					OBJECT-TYPE
	 SYNTAX Gauge
	 ACCESS read-only
	 STATUS mandatory
	 DESCRIPTION
		"The number of Degraded Minutes  (DMs)  encoun-
		tered  by  a  DS1  interface in the previous 24
		hour interval."
	 ::= { dsx1FarEndTotalEntry 10 }


-- the DSX Channel Owner Table

-- Implementation of this table is mandatory for T1/E1
-- Back Cards  dividing a DSX into channels containing different
-- data streams that are of local interest. 

--      For North American (DS1) interfaces, there are 24 legal
--      channels, numbered 1 through 24.

--      For G.704 interfaces, there are 31 legal channels,
--      numbered 1 through 31.  The channels (1..31) correspond
--      directly to the equivalently numbered time-slots.

 dsx1ChanOwnerTable 					OBJECT-TYPE
	 SYNTAX  SEQUENCE OF Dsx1ChanOwnerEntry
	 ACCESS	not-accessible
	 STATUS  mandatory
	 DESCRIPTION
		"The DS1 Channel-to-Port mapping table."
	::= { dsx 8 }


 dsx1ChanOwnerEntry 					OBJECT-TYPE
	 SYNTAX  Dsx1ChanOwnerEntry
	 ACCESS  not-accessible
	 STATUS  mandatory
	 DESCRIPTION
		"An entry in the dsx1ChanOwner table, indexed by channel
		 showing which logical port owns this channel. An entry of
		 -1 depicts a channel that is freely assignable."
	INDEX   { dsx1ChanIndex }
	::= { dsx1ChanOwnerTable 1 }

Dsx1ChanOwnerEntry ::=
  SEQUENCE {
	 	dsx1ChanIndex	 	INTEGER,
		dsx1ChanOwnerPort       INTEGER
  }


 dsx1ChanIndex 						OBJECT-TYPE
	 SYNTAX  INTEGER (0..31)
	 ACCESS  read-only
	 STATUS  mandatory
	 DESCRIPTION
		"The index value which uniquely identifies  the
		DSX channel to which this entry is applicable."
	::= { dsx1ChanOwnerEntry 1 }


 dsx1ChanOwnerPort					OBJECT-TYPE
	 SYNTAX  INTEGER (-1..128)
	 ACCESS  read-write
	 STATUS  mandatory
	 DESCRIPTION
		"The number of the port to which this channel is assigned."
	::= { dsx1ChanOwnerEntry 2 }

-- the DSX Channel Group (or logical port) Mode Table

-- Implementation of this table is mandatory for T1/E1
-- Back Cards.  It specifies the mode (either DS0 or 56K)
-- that logical data streams comprising ports are using.
-- Note that an ESF signal may be groomed to the Back Card
-- wherein the various logical channel groupings use 
-- differing modes.  This occurs frequently when the groomed
-- channel groups come to the Back Card I/F via carrier
-- facilities of differing capability.

 dsx1PortModeTable 					OBJECT-TYPE
	 SYNTAX  SEQUENCE OF Dsx1PortModeEntry
	 ACCESS	not-accessible
	 STATUS  mandatory
	 DESCRIPTION
		"The DS1 Logical Port-to-Mode mapping table."
	::= { dsx 9 }


 dsx1PortModeEntry 					OBJECT-TYPE
	 SYNTAX  Dsx1PortModeEntry
	 ACCESS  not-accessible
	 STATUS  mandatory
	 DESCRIPTION
		"An entry in the DS1 Port->Mode table, indexed by port
		 showing which mode this port runs in. An entry of
		 0  depicts a port that is operating in the DS0 mode,
		 a non-zero entry indicates the 56K mode. Note that a
		 DS1 link operating JBZS will always have all of its
  		 channels operating in 56K mode."
	INDEX   { dsx1PortIndex }
	::= { dsx1PortModeTable 1 }


Dsx1PortModeEntry ::=
	SEQUENCE { 
		dsx1PortMode		INTEGER (1..2),
		dsx1PortIndex		INTEGER (0..255)
	}

dsx1PortMode						OBJECT-TYPE
	SYNTAX INTEGER { 
		modeDS0(1),
		mode56K(2)
	}
	ACCESS  read-write
	STATUS  mandatory
	DESCRIPTION
		"The port mode of the T1/E1 Back Card port to
		 which this entry is applicable."
	::= { dsx1PortModeEntry 1 }

dsx1PortIndex 						OBJECT-TYPE
	SYNTAX  INTEGER (0..255)
	ACCESS  read-only
	STATUS  mandatory
	DESCRIPTION
		"The index value which uniquely identifies  the
		T1/E1 Back Card port to which this entry is applicable."
	::= { dsx1PortModeEntry 2 }

--
--
-- Filesystem Group
--
--
exportFileSystem					OBJECT-TYPE
	SYNTAX	INTEGER {
			notExported(1),
			exported(2)
		}
	ACCESS	read-write
	STATUS	mandatory
	DESCRIPTION
		"Determines whether this node will export its filesystem.
		 The default will be <notExported>. This variable can be
		 changed by the FrameXpress Node Manager. When the agent
		 receives the request to change this variable to <exported>,
		 it attempts to export the file system prior to responding
		 to the Node Manager. If the export fails, the SNMP request
		 will fail sending a failure response to the Manager."
	::= { filesystem 1 }

loadAndExecute						OBJECT-TYPE
	SYNTAX	INTEGER {
			notloading(1),
			loading(2)
		}
	ACCESS	read-write
	STATUS	mandatory
	DESCRIPTION
		"Triggers the loading of SNMPCNF.CMD if such a file
		 existed, otherwise, it triggers the loading of
		 DEFAULT.CFG after clearing the current configuration."
	::= { filesystem 2 }


--
-- the trap definitions themselves 
--

systemRestartTrap					TRAP-TYPE
	ENTERPRISE		frx
	DESCRIPTION
		"This trap is sent when the system restarts for any reason
		 other than an operator requested restart." 
	::= 1

systemSyserrTrap					TRAP-TYPE
	ENTERPRISE		frx
	DESCRIPTION
		"This trap is sent when the system detects a
		 inconsistency. This may cause a reset of the FRX node." 
	::= 2

configChangedTrap					TRAP-TYPE
	ENTERPRISE		frx
	DESCRIPTION
		"This trap is sent when a new configuration is saved in
		 the non-volatile storage." 
	::= 3 

nodeCongestedTrap					TRAP-TYPE
	ENTERPRISE		frx
	DESCRIPTION
		"This trap is sent when the FRX node becomes congested."
	::= 4

portInstalledTrap					TRAP-TYPE
	ENTERPRISE		frx
	VARIABLES		{ portConfEntryId }
	DESCRIPTION
		"This trap is sent when a port is installed."
	::= 5

portDeletedTrap						TRAP-TYPE
	ENTERPRISE		frx
	VARIABLES		{ portConfEntryId }
	DESCRIPTION
		"This trap is sent when a port is deleted."
	::= 6

portActivatedTrap					TRAP-TYPE
	ENTERPRISE		frx
	VARIABLES		{ portConfEntryId }
	DESCRIPTION
		"This trap is sent when a port is activated."
	::= 7

portDisabledTrap					TRAP-TYPE
	ENTERPRISE		frx
	VARIABLES		{ portConfEntryId }
	DESCRIPTION
		"This trap is sent when a port is disabled."
	::= 8

portCongestedTrap					TRAP-TYPE
	ENTERPRISE		frx
	VARIABLES		{ portConfEntryId }
	DESCRIPTION
		"This trap is sent when a port is congested."
	::= 9


pvcInstalledTrap					TRAP-TYPE
	ENTERPRISE		frx
	VARIABLES		{ portConfEntryId,circuitConfDLCI }
	DESCRIPTION
		"This trap is sent when a virtual circuit is installed."
	::= 10

pvcDeletedTrap						TRAP-TYPE
	ENTERPRISE		frx
	VARIABLES		{ portConfEntryId, circuitConfDLCI }
	DESCRIPTION
		"This trap is sent when a virtual circuit is deleted."
	::= 11

pvcActivatedTrap					TRAP-TYPE
	ENTERPRISE		frx
	VARIABLES		{ portConfEntryId, circuitConfDLCI }
	DESCRIPTION
		"This trap is sent when a virtual circuit is activated."
	::= 12

pvcDisabledTrap						TRAP-TYPE
	ENTERPRISE		frx
	VARIABLES		{ portConfEntryId, circuitConfDLCI }
	DESCRIPTION
		"This trap is sent when a virtual circuit is disabled."
	::= 13

pvcStatusActiveTrap					TRAP-TYPE
	ENTERPRISE		frx
	VARIABLES		{ portConfEntryId, circuitConfDLCI }
	DESCRIPTION
		"This trap is sent when the status for a virtual circuit
		 become active." 
	::= 14

pvcStatusInactiveTrap					TRAP-TYPE
	ENTERPRISE		frx
	VARIABLES		{ portConfEntryId, circuitConfDLCI }
	DESCRIPTION
		"This trap is sent when the status for a virtual circuit
		 become inactive." 
	::= 15

cbusUpTrap						TRAP-TYPE
	ENTERPRISE		frx
	DESCRIPTION
		"This trap is sent when the CBUS interface is ready for
		 use." 
	::= 16

cbusDownTrap						TRAP-TYPE
	ENTERPRISE		frx
	DESCRIPTION
		"This trap is sent when the CBUS interface becomes
		 invalid." 
	::= 17

serialFailTrap						TRAP-TYPE
	ENTERPRISE		frx
	VARIABLES		{ portStatusEntryId }
	DESCRIPTION
		"This trap is sent when an HDLC port fails to initialize."
	::= 18

portUniActiveTrap					TRAP-TYPE
	ENTERPRISE		frx
	VARIABLES		{ portStatusEntryId }
	DESCRIPTION
		"This trap is sent when a port's UNI protocol becomes
		 active." 
	::= 19

portUniInactiveTrap					TRAP-TYPE
	ENTERPRISE		frx
	VARIABLES		{ portStatusEntryId }
	DESCRIPTION
		"This trap is sent when a port's UNI protocol becomes
		 inactive." 
	::= 20

portIDNXCallUpTrap					TRAP-TYPE
	ENTERPRISE		frx
	VARIABLES		{ portStatusEntryId }
	DESCRIPTION
		"This trap is sent when a port's IDNX call (bandwidth) is
		 available." 
	::= 21

portIDNXCallDownTrap					TRAP-TYPE
	ENTERPRISE		frx
	VARIABLES		{ portStatusEntryId }
	DESCRIPTION
		"This trap is sent when a port's IDNX call (bandwidth)
		 becomes unavailable." 
	::= 22

nodeNotCongestedTrap					TRAP-TYPE
	ENTERPRISE		frx
	DESCRIPTION
		"This trap is sent when a FRX node goes from being
		 congested to not being congested." 
	::= 23

portNotCongestedTrap					TRAP-TYPE
	ENTERPRISE		frx
	VARIABLES		{ portStatusEntryId }
	DESCRIPTION
		"This trap is sent when a port goes from being congested
		 to not being congested." 
	::= 24

operatorResetTrap					TRAP-TYPE
	ENTERPRISE		frx
	DESCRIPTION
		"This trap is sent when the operator requests a reset of
		 the FRX." 
	::= 25

eventLogClearedTrap					TRAP-TYPE
	ENTERPRISE		frx
	DESCRIPTION
		"This trap is sent when the operator requests to clear the
		 FRX event log." 
	::= 26

configClearedTrap					TRAP-TYPE
	ENTERPRISE		frx
	DESCRIPTION
		"This trap is sent when the operator requests to clear the
		 configuration of an FRX." 
	::= 27

functionMismatchTrap					TRAP-TYPE
	ENTERPRISE		frx
	DESCRIPTION
		"This trap is sent when the code type (FRX) does not match
		 the value stored in the IDNX database." 
	::= 28

eventLogErrorTrap					TRAP-TYPE
	ENTERPRISE		frx
	DESCRIPTION
		"This trap is sent when the FRX is unable to create an
		 event log." 
	::= 29

encapActiveTrap						TRAP-TYPE
	ENTERPRISE		frx
	DESCRIPTION
		"This trap is sent when frame relay encapsulation is
		 turned on for a PVC." 
	::= 30

encapInactiveTrap					TRAP-TYPE
	ENTERPRISE		frx
	DESCRIPTION
		"This trap is sent when frame relay encapsulation is
		 turned off for a PVC." 
	::= 31

altPathUsedTrap						TRAP-TYPE
	ENTERPRISE		frx
	DESCRIPTION
		"This trap is sent when a path alternate to the preferred
		 path is used to setup a pvc." 
	::= 32

pvcStateIdleTrap					TRAP-TYPE
	ENTERPRISE		frx
	VARIABLES		{ portConfEntryId, circuitConfDLCI }
	DESCRIPTION
		"The state of a PVC describes the current status of call
		 setup. This trap is sent when a PVC's state changes to
		 Idle."   
	::= 33

pvcStateSetupTrap					TRAP-TYPE
	ENTERPRISE		frx
	VARIABLES		{ portConfEntryId, circuitConfDLCI }
	DESCRIPTION
		"The state of a PVC describes the current status of call
		 setup. This trap is sent when a PVC's state changes to
		 Setup."   
	::= 34

pvcStateCompleteTrap					TRAP-TYPE
	ENTERPRISE		frx
	VARIABLES		{ portConfEntryId, circuitConfDLCI }
	DESCRIPTION
		"The state of a PVC describes the current status of call
		 setup. This trap is sent when a PVC's state changes to
		 Complete."   
	::= 35

pvcStateDisconnectTrap					TRAP-TYPE
	ENTERPRISE		frx
	VARIABLES		{ portConfEntryId, circuitConfDLCI }
	DESCRIPTION
		"The state of a PVC describes the current status of call
		 setup. This trap is sent when a PVC's state changes to
		 Disconnect."   
	::= 36

billingDownloadSuccessTrap				TRAP-TYPE
	ENTERPRISE		frx
	DESCRIPTION
		"A Billing file was successfully downloaded from the FRX."
	::= 37

billingDownloadFailureTrap				TRAP-TYPE
	ENTERPRISE		frx
	DESCRIPTION
		"An error occurred while the FRX attempted to download
		 a Billing file."
	::= 38

--
-- 10jan96
--
-- Trap numbers 39 through 67 hve been shifted to 50 through 78.
-- New trap numbers 39 through 42 have been added below.
--

billingDownloadThresholdTrap				TRAP-TYPE
	ENTERPRISE		frx
	DESCRIPTION
		"An attempt was made to set an obsolete Billing download
		 threshold parameter."
	::= 39

configSyntaxErrorTrap				TRAP-TYPE
	ENTERPRISE		frx
	DESCRIPTION
		"A line in the FRX configuration file had a syntax
		 error when it was loaded; the line was ignored."
	::= 40

configDownloadSuccessTrap				TRAP-TYPE
	ENTERPRISE		frx
	DESCRIPTION
		"A Configuration file was successfully downloaded from
		 the FRX."
	::= 41

configDownloadFailureTrap				TRAP-TYPE
	ENTERPRISE		frx
	DESCRIPTION
		"An error occurred while the FRX attempted to download
		 a Configuration file."
	::= 42


--
-- 10jan96
--
-- Trap numbers 39 through 67 hve been shifted to 50 through 78.
-- New trap numbers 39 through 42 have been added above.
--
-- Trap numbers 43 through 49 are reserved for 2.01.xx bug fixes.
-- They may be added in the future.
--

nodeFlashMemErr						TRAP-TYPE
	ENTERPRISE		frx
	DESCRIPTION
		"This trap indicates that a code checksum error occurred in Flash."
	::= 50

nodeFlashWriteErr					TRAP-TYPE
	ENTERPRISE		frx
	DESCRIPTION
		"This trap indicates that a code transfer to Flash occurred. Flash may
		 now be corrupted."
	::= 51

nodeUserLogin						TRAP-TYPE
	ENTERPRISE		frx
	DESCRIPTION
		"A user has logged into the FRX through the serial console or network."
	::= 52

nodeUserLogout						TRAP-TYPE
	ENTERPRISE		frx
	DESCRIPTION
		"A user has logged out."
	::= 53

dsx1NoAlarm						TRAP-TYPE
	ENTERPRISE		frx
	DESCRIPTION
		"No alarm present."
	::= 54

dsx1RcvFarEndLOF					TRAP-TYPE
	ENTERPRISE		frx
	DESCRIPTION
		"Far end LOF (a.k.a. Yellow Alarm)."
	::= 55

dsx1RcvFarEndLOFEnded					TRAP-TYPE
	ENTERPRISE		frx
	DESCRIPTION
		"Far end LOF (a.k.a. Yellow Alarm) indication has ended."
	::= 56

dsx1XmtFarEndLOF        				TRAP-TYPE
	ENTERPRISE		frx
	DESCRIPTION
		"Near end sending LOF Indication."
	::= 57

dsx1XmtFarEndLOFEnding        				TRAP-TYPE
	ENTERPRISE		frx
	DESCRIPTION
		"Near end ending LOF Indication."
	::= 58

dsx1RcvAIS              				TRAP-TYPE
	ENTERPRISE		frx
	DESCRIPTION
		"Far end sending AIS."
	::= 59

dsx1RcvAISEnded             				TRAP-TYPE
	ENTERPRISE		frx
	DESCRIPTION
		"Far end AIS has ceased."
	::= 60

dsx1XmtAIS              				TRAP-TYPE
	ENTERPRISE		frx
	DESCRIPTION
		"Near end sending AIS indication."
	::= 61

dsx1XmtAISEnding              				TRAP-TYPE
	ENTERPRISE		frx
	DESCRIPTION
		"Near end ending AIS indication."
	::= 62

dsx1LossOfFrame         				TRAP-TYPE
	ENTERPRISE		frx
	DESCRIPTION
		"Near end LOF (a.k.a. Red Alarm)."
	::= 63

dsx1LossOfFrameEnded      				TRAP-TYPE
	ENTERPRISE		frx
	DESCRIPTION
		"Near end LOF (a.k.a. Red Alarm) indication has ended."
	::= 64

dsx1LossOfSignal        				TRAP-TYPE
	ENTERPRISE		frx
	DESCRIPTION
		"Near end Loss Of Signal."
	::= 65

dsx1LossOfSignalEnded     				TRAP-TYPE
	ENTERPRISE		frx
	DESCRIPTION
		"Near end Loss Of Signal indication has ended."
	::= 66

dsx1LoopbackState       				TRAP-TYPE
	ENTERPRISE		frx
	DESCRIPTION
		"Near end is looped."
	::= 67

dsx1LoopbackStateEnded       				TRAP-TYPE
	ENTERPRISE		frx
	DESCRIPTION
		"Near end is un-looped."
	::= 68

dsx1T16AIS              				TRAP-TYPE
	ENTERPRISE		frx
	DESCRIPTION
		"E1 TS16 AIS indication received."
	::= 69

dsx1T16AISEnded            				TRAP-TYPE
	ENTERPRISE		frx
	DESCRIPTION
		"E1 TS16 AIS indication has ended."
	::= 70

dsx1RcvFarEndLOMF       				TRAP-TYPE
	ENTERPRISE		frx
	DESCRIPTION
		"Far End sending TS16 LOMF."
	::= 71

dsx1RcvFarEndLOMFEnded     				TRAP-TYPE
	ENTERPRISE		frx
	DESCRIPTION
		"Far End ending TS16 LOMF."
	::= 72

dsx1XmtFarEndLOMF       				TRAP-TYPE
	ENTERPRISE		frx
	DESCRIPTION
		"Near End sending TS16 LOMF."
	::= 73

dsx1XmtFarEndLOMFEnding       				TRAP-TYPE
	ENTERPRISE		frx
	DESCRIPTION
		"Near End ending TS16 LOMF."
	::= 74

dsx1RcvTestCode         				TRAP-TYPE
	ENTERPRISE		frx
	DESCRIPTION
		"Near End detected a test code."
	::= 75

dsx1OtherFailure        				TRAP-TYPE
	ENTERPRISE		frx
	DESCRIPTION
		"Unknown line status received."
	::= 76

nodeAlarmedPortsZero					TRAP-TYPE
	ENTERPRISE		frx
	DESCRIPTION
		"The value of nodeAlarmedPorts became zero."
	::= 77

portAlarmedPVCsZero					TRAP-TYPE
	ENTERPRISE		frx
	VARIABLES		{ portConfEntryId }
	DESCRIPTION
		"The value of portAlarmedPVCs for this port became zero."
	::= 78

operatorInstallTrap					TRAP-TYPE
	ENTERPRISE		frx
	DESCRIPTION
		"This trap is sent when a new operator is installed." 
	::= 79

operatorDeleteTrap					TRAP-TYPE
	ENTERPRISE		frx
	DESCRIPTION
		"This trap is sent when an operator is deleted." 
	::= 80

END
