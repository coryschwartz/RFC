NCD-MIB-1 DEFINITIONS ::= BEGIN

-- Title:	NCD MIB
-- Date:	October 16, 1990
-- By:		Kim Dimick <dimick@ncd.com>

		IMPORTS
			private, enterprises, OBJECT-TYPE, NetworkAddress,
			IpAddress, Counter, Gauge, TimeTicks
			    FROM RFC1065-SMI;

		  ncd OBJECT IDENTIFIER ::= { enterprises 82 }
		  ncd-products OBJECT IDENTIFIER ::= { ncd 1 }
		  ncd16 OBJECT IDENTIFIER ::= { ncd-products 1 }
		  ncd19 OBJECT IDENTIFIER ::= { ncd-products 2 }
		  ncd17c OBJECT IDENTIFIER ::= { ncd-products 3 }
		  ncd16e OBJECT IDENTIFIER ::= { ncd-products 4 }
		  ncd-mibs OBJECT IDENTIFIER ::= { ncd 2 }
		  ncd-mibs-mib1 OBJECT IDENTIFIER ::= { ncd-mibs 1 }

		  ncdSystem OBJECT IDENTIFIER ::= { ncd-mibs-mib1 1 }
		  ncdMbuf OBJECT IDENTIFIER ::= { ncd-mibs-mib1 2 }
		  ncdEther OBJECT IDENTIFIER ::= { ncd-mibs-mib1 3 }
		  ncdSerial OBJECT IDENTIFIER ::= { ncd-mibs-mib1 4 }
		  ncdTcp OBJECT IDENTIFIER ::= { ncd-mibs-mib1 5 }
		  -- ncdUdp OBJECT IDENTIFIER ::= { ncd-mibs-mib1 6 }
		  ncdTftp OBJECT IDENTIFIER ::= { ncd-mibs-mib1 7 }
		  ncdNfs OBJECT IDENTIFIER ::= { ncd-mibs-mib1 8 }

		  -- NCD System Group

                  ncdSysMemTotal OBJECT-TYPE
                          SYNTAX  INTEGER
                          ACCESS  read-only
                          STATUS  optional
                          ::= { ncdSystem 1 }

                  ncdSysMemAvail OBJECT-TYPE
                          SYNTAX  Gauge
                          ACCESS  read-only
                          STATUS  optional
                          ::= { ncdSystem 2 }

                  ncdSysMemFrags OBJECT-TYPE
                          SYNTAX  Gauge
                          ACCESS  read-only
                          STATUS  optional
                          ::= { ncdSystem 3 }

                  ncdSysIdleTime OBJECT-TYPE
                          SYNTAX  TimeTicks
                          ACCESS  read-only
                          STATUS  optional
                          ::= { ncdSystem 4 }

		  -- NCD Mbuf Group

                  ncdMbufTotal OBJECT-TYPE
                          SYNTAX  INTEGER
                          ACCESS  read-only
                          STATUS  optional
                          ::= { ncdMbuf 1 }

                  ncdMbufFree OBJECT-TYPE
                          SYNTAX  Gauge
                          ACCESS  read-only
                          STATUS  optional
                          ::= { ncdMbuf 2 }

                  ncdMbufClusterTotal OBJECT-TYPE
                          SYNTAX  INTEGER
                          ACCESS  read-only
                          STATUS  optional
                          ::= { ncdMbuf 3 }

                  ncdMbufClusterFree OBJECT-TYPE
                          SYNTAX  Gauge
                          ACCESS  read-only
                          STATUS  optional
                          ::= { ncdMbuf 4 }

                  ncdMbufReserved OBJECT-TYPE
                          SYNTAX  Gauge
                          ACCESS  read-only
                          STATUS  optional
                          ::= { ncdMbuf 5 }

                  ncdMbufDrops OBJECT-TYPE
                          SYNTAX  Counter
                          ACCESS  read-only
                          STATUS  optional
                          ::= { ncdMbuf 6 }

                  ncdMbufWaits OBJECT-TYPE
                          SYNTAX  Counter
                          ACCESS  read-only
                          STATUS  optional
                          ::= { ncdMbuf 7 }

                  ncdMbufData OBJECT-TYPE
                          SYNTAX  Gauge
                          ACCESS  read-only
                          STATUS  optional
                          ::= { ncdMbuf 8 }

                  ncdMbufHeader OBJECT-TYPE
                          SYNTAX  Gauge
                          ACCESS  read-only
                          STATUS  optional
                          ::= { ncdMbuf 9 }

                  ncdMbufSocket OBJECT-TYPE
                          SYNTAX  Gauge
                          ACCESS  read-only
                          STATUS  optional
                          ::= { ncdMbuf 10 }

                  ncdMbufProtoCtrlBlock OBJECT-TYPE
                          SYNTAX  Gauge
                          ACCESS  read-only
                          STATUS  optional
                          ::= { ncdMbuf 11 }

                  ncdMbufRouteTable OBJECT-TYPE
                          SYNTAX  Gauge
                          ACCESS  read-only
                          STATUS  optional
                          ::= { ncdMbuf 12 }

                  ncdMbufAtTable OBJECT-TYPE
                          SYNTAX  Gauge
                          ACCESS  read-only
                          STATUS  optional
                          ::= { ncdMbuf 13 }

                  ncdMbufSocketName OBJECT-TYPE
                          SYNTAX  Gauge
                          ACCESS  read-only
                          STATUS  optional
                          ::= { ncdMbuf 14 }

                  ncdMbufSocketOptions OBJECT-TYPE
                          SYNTAX  Gauge
                          ACCESS  read-only
                          STATUS  optional
                          ::= { ncdMbuf 15 }

                  ncdMbufFrags OBJECT-TYPE
                          SYNTAX  Gauge
                          ACCESS  read-only
                          STATUS  optional
                          ::= { ncdMbuf 16 }

                  ncdMbufInterfaceAddr OBJECT-TYPE
                          SYNTAX  Gauge
                          ACCESS  read-only
                          STATUS  optional
                          ::= { ncdMbuf 17 }

		  -- NCD Ether Group

                  -- the ether interface table

                  ncdEtherTable OBJECT-TYPE
                          SYNTAX  SEQUENCE OF NcdEtherEntry
                          ACCESS  read-write
                          STATUS  optional
                          ::= { ncdEther 1 }

                  ncdEtherEntry OBJECT-TYPE
                          SYNTAX  NcdEtherEntry
                          ACCESS  read-write
                          STATUS  optional
                          ::= { ncdEtherTable 1 }

                  NcdEtherEntry ::= SEQUENCE {
		      ncdEtherInCrcErrors
			  Counter,
		      ncdEtherInMissed
			  Counter,
		      ncdEtherInFrameErrors
			  Counter,
		      ncdEtherSingleCollisions
			  Counter,
		      ncdEtherMultipleCollisions
			  Counter,
		      ncdEtherLateCollisions
			  Counter,
		      ncdEtherOutDeferred
			  Counter,
		      ncdEtherOutRetryErrors
			  Counter,
		      ncdEtherLostCarrier
			  Counter,
		      ncdEtherRestarts
			  Counter
                  }

                  ncdEtherInCrcErrors OBJECT-TYPE
                          SYNTAX  Counter
                          ACCESS  read-only
                          STATUS  optional
                          ::= { ncdEtherEntry 1 }

                  ncdEtherInMissed OBJECT-TYPE
                          SYNTAX  Counter
                          ACCESS  read-only
                          STATUS  optional
                          ::= { ncdEtherEntry 2 }

                  ncdEtherInFrameErrors OBJECT-TYPE
                          SYNTAX  Counter
                          ACCESS  read-only
                          STATUS  optional
                          ::= { ncdEtherEntry 3 }

                  ncdEtherSingleCollisions OBJECT-TYPE
                          SYNTAX  Counter
                          ACCESS  read-only
                          STATUS  optional
                          ::= { ncdEtherEntry 4 }

                  ncdEtherMultipleCollisions OBJECT-TYPE
                          SYNTAX  Counter
                          ACCESS  read-only
                          STATUS  optional
                          ::= { ncdEtherEntry 5 }

                  ncdEtherLateCollisions OBJECT-TYPE
                          SYNTAX  Counter
                          ACCESS  read-only
                          STATUS  optional
                          ::= { ncdEtherEntry 6 }

                  ncdEtherOutDeferred OBJECT-TYPE
                          SYNTAX  Counter
                          ACCESS  read-only
                          STATUS  optional
                          ::= { ncdEtherEntry 7 }

                  ncdEtherOutRetryErrors OBJECT-TYPE
                          SYNTAX  Counter
                          ACCESS  read-only
                          STATUS  optional
                          ::= { ncdEtherEntry 8 }

                  ncdEtherLostCarrier OBJECT-TYPE
                          SYNTAX  Counter
                          ACCESS  read-only
                          STATUS  optional
                          ::= { ncdEtherEntry 9 }

                  ncdEtherRestarts OBJECT-TYPE
                          SYNTAX  Counter
                          ACCESS  read-only
                          STATUS  optional
                          ::= { ncdEtherEntry 10 }

		  -- NCD Serial Group

                  -- the serial interface table

                  ncdSerialTable OBJECT-TYPE
                          SYNTAX  SEQUENCE OF NcdSerialEntry
                          ACCESS  read-write
                          STATUS  optional
                          ::= { ncdSerial 1 }

                  ncdSerialEntry OBJECT-TYPE
                          SYNTAX  NcdSerialEntry
                          ACCESS  read-write
                          STATUS  optional
                          ::= { ncdSerialTable 1 }

                  NcdSerialEntry ::= SEQUENCE {
		      ncdSerialInOverruns
			  Counter,
		      ncdSerialInFrameErrors
			  Counter,
                      ncdSerialInParityErrors
			  Counter,
                      ncdSerialInBreakErrors
			  Counter
                  }

                  ncdSerialInOverruns OBJECT-TYPE
                          SYNTAX  Counter
                          ACCESS  read-only
                          STATUS  optional
                          ::= { ncdSerialEntry 1 }

                  ncdSerialInFrameErrors OBJECT-TYPE
                          SYNTAX  Counter
                          ACCESS  read-only
                          STATUS  optional
                          ::= { ncdSerialEntry 2 }

                  ncdSerialInParityErrors OBJECT-TYPE
                          SYNTAX  Counter
                          ACCESS  read-only
                          STATUS  optional
                          ::= { ncdSerialEntry 3 }

                  ncdSerialInBreakErrors OBJECT-TYPE
                          SYNTAX  Counter
                          ACCESS  read-only
                          STATUS  optional
                          ::= { ncdSerialEntry 4 }

		  -- NCD TCP Group

                  ncdTcpRetransDrops OBJECT-TYPE
                          SYNTAX  Counter
                          ACCESS  read-only
                          STATUS  optional
                          ::= { ncdTcp 1 }

                  ncdTcpOutKeepAlives OBJECT-TYPE
                          SYNTAX  Counter
                          ACCESS  read-only
                          STATUS  optional
                          ::= { ncdTcp 2 }

                  ncdTcpKeepAliveDrops OBJECT-TYPE
                          SYNTAX  Counter
                          ACCESS  read-only
                          STATUS  optional
                          ::= { ncdTcp 3 }

                  ncdTcpInAcks OBJECT-TYPE
                          SYNTAX  Counter
                          ACCESS  read-only
                          STATUS  optional
                          ::= { ncdTcp 4 }

                  ncdTcpOutBareAcks OBJECT-TYPE
                          SYNTAX  Counter
                          ACCESS  read-only
                          STATUS  optional
                          ::= { ncdTcp 5 }

		  -- NCD TFTP Group

                  ncdTftpClientReadReqs OBJECT-TYPE
                          SYNTAX  Counter
                          ACCESS  read-only
                          STATUS  optional
                          ::= { ncdTftp 1 }

                  ncdTftpClientWriteReqs OBJECT-TYPE
                          SYNTAX  Counter
                          ACCESS  read-only
                          STATUS  optional
                          ::= { ncdTftp 2 }

                  ncdTftpClientInDataPkts OBJECT-TYPE
                          SYNTAX  Counter
                          ACCESS  read-only
                          STATUS  optional
                          ::= { ncdTftp 3 }

                  ncdTftpClientInAcks OBJECT-TYPE
                          SYNTAX  Counter
                          ACCESS  read-only
                          STATUS  optional
                          ::= { ncdTftp 4 }

                  ncdTftpClientInNoFileErrors OBJECT-TYPE
                          SYNTAX  Counter
                          ACCESS  read-only
                          STATUS  optional
                          ::= { ncdTftp 5 }

                  ncdTftpClientInAccessErrors OBJECT-TYPE
                          SYNTAX  Counter
                          ACCESS  read-only
                          STATUS  optional
                          ::= { ncdTftp 6 }

                  ncdTftpClientInDiskFullErrors OBJECT-TYPE
                          SYNTAX  Counter
                          ACCESS  read-only
                          STATUS  optional
                          ::= { ncdTftp 7 }

                  ncdTftpClientNoBufs OBJECT-TYPE
                          SYNTAX  Counter
                          ACCESS  read-only
                          STATUS  optional
                          ::= { ncdTftp 8 }

                  ncdTftpClientOutDataPkts OBJECT-TYPE
                          SYNTAX  Counter
                          ACCESS  read-only
                          STATUS  optional
                          ::= { ncdTftp 9 }

                  ncdTftpClientOutAcks OBJECT-TYPE
                          SYNTAX  Counter
                          ACCESS  read-only
                          STATUS  optional
                          ::= { ncdTftp 10 }

                  ncdTftpClientRetrans OBJECT-TYPE
                          SYNTAX  Counter
                          ACCESS  read-only
                          STATUS  optional
                          ::= { ncdTftp 11 }

                  ncdTftpClientRetries OBJECT-TYPE
                          SYNTAX  INTEGER
                          ACCESS  read-write
                          STATUS  optional
                          ::= { ncdTftp 12 }

                  ncdTftpClientTimeout OBJECT-TYPE
                          SYNTAX  TimeTicks
                          ACCESS  read-write
                          STATUS  optional
                          ::= { ncdTftp 13 }

		  -- NCD NFS Group

                  ncdNfsClientNulls OBJECT-TYPE
                          SYNTAX  Counter
                          ACCESS  read-only
                          STATUS  optional
                          ::= { ncdNfs 1 }

                  ncdNfsClientGetAttributes OBJECT-TYPE
                          SYNTAX  Counter
                          ACCESS  read-only
                          STATUS  optional
                          ::= { ncdNfs 2 }

                  ncdNfsClientSetAttributes OBJECT-TYPE
                          SYNTAX  Counter
                          ACCESS  read-only
                          STATUS  optional
                          ::= { ncdNfs 3 }

                  ncdNfsClientGetRoots OBJECT-TYPE
                          SYNTAX  Counter
                          ACCESS  read-only
                          STATUS  optional
                          ::= { ncdNfs 4 }

                  ncdNfsClientLookups OBJECT-TYPE
                          SYNTAX  Counter
                          ACCESS  read-only
                          STATUS  optional
                          ::= { ncdNfs 5 }

                  ncdNfsClientReadLinks OBJECT-TYPE
                          SYNTAX  Counter
                          ACCESS  read-only
                          STATUS  optional
                          ::= { ncdNfs 6 }

                  ncdNfsClientReads OBJECT-TYPE
                          SYNTAX  Counter
                          ACCESS  read-only
                          STATUS  optional
                          ::= { ncdNfs 7 }

                  ncdNfsClientWriteCaches OBJECT-TYPE
                          SYNTAX  Counter
                          ACCESS  read-only
                          STATUS  optional
                          ::= { ncdNfs 8 }

                  ncdNfsClientWrites OBJECT-TYPE
                          SYNTAX  Counter
                          ACCESS  read-only
                          STATUS  optional
                          ::= { ncdNfs 9 }

                  ncdNfsClientCreates OBJECT-TYPE
                          SYNTAX  Counter
                          ACCESS  read-only
                          STATUS  optional
                          ::= { ncdNfs 10 }

                  ncdNfsClientRemoves OBJECT-TYPE
                          SYNTAX  Counter
                          ACCESS  read-only
                          STATUS  optional
                          ::= { ncdNfs 11 }

                  ncdNfsClientRenames OBJECT-TYPE
                          SYNTAX  Counter
                          ACCESS  read-only
                          STATUS  optional
                          ::= { ncdNfs 12 }

                  ncdNfsClientCreateLinks OBJECT-TYPE
                          SYNTAX  Counter
                          ACCESS  read-only
                          STATUS  optional
                          ::= { ncdNfs 13 }

                  ncdNfsClientCreateSymlinks OBJECT-TYPE
                          SYNTAX  Counter
                          ACCESS  read-only
                          STATUS  optional
                          ::= { ncdNfs 14 }

                  ncdNfsClientMakeDir OBJECT-TYPE
                          SYNTAX  Counter
                          ACCESS  read-only
                          STATUS  optional
                          ::= { ncdNfs 15 }

                  ncdNfsClientRemoveDir OBJECT-TYPE
                          SYNTAX  Counter
                          ACCESS  read-only
                          STATUS  optional
                          ::= { ncdNfs 16 }

                  ncdNfsClientReadDir OBJECT-TYPE
                          SYNTAX  Counter
                          ACCESS  read-only
                          STATUS  optional
                          ::= { ncdNfs 17 }

                  ncdNfsClientStatFileSys OBJECT-TYPE
                          SYNTAX  Counter
                          ACCESS  read-only
                          STATUS  optional
                          ::= { ncdNfs 18 }

                  -- the NFS client mount table

                  ncdNfsMountTable OBJECT-TYPE
                          SYNTAX  SEQUENCE OF NcdNfsMountEntry
                          ACCESS  read-write
                          STATUS  optional
                          ::= { ncdNfs 19 }

                  ncdNfsMountEntry OBJECT-TYPE
                          SYNTAX  NcdNfsMountEntry
                          ACCESS  read-write
                          STATUS  optional
                          ::= { ncdNfsMountTable 1 }

                  NcdNfsMountEntry ::= SEQUENCE {
		      ncdNfsMountEntryIndex
			  INTEGER,
		      ncdNfsMountEntryLocalDir
			  OCTET STRING,
                      ncdNfsMountEntryServerAddr
                          IpAddress,
                      ncdNfsMountEntryServerDir
			  OCTET STRING,
                      ncdNfsMountEntryReadSize
                          INTEGER (1..8192),
                      ncdNfsMountEntryWriteSize
                          INTEGER (1..8192),
                      ncdNfsMountEntryRetries
                          INTEGER,
                      ncdNfsMountEntryTimeout
                          INTEGER
                  }

                  ncdNfsMountEntryIndex OBJECT-TYPE
                          SYNTAX  INTEGER
                          ACCESS  read-only
                          STATUS  optional
                          ::= { ncdNfsMountEntry 1 }

                  ncdNfsMountEntryLocalDir OBJECT-TYPE
                          SYNTAX  OCTET STRING
                          ACCESS  read-only
                          STATUS  optional
                          ::= { ncdNfsMountEntry 2 }

                  ncdNfsMountEntryServerAddr OBJECT-TYPE
                          SYNTAX  NetworkAddress
                          ACCESS  read-only
                          STATUS  optional
                          ::= { ncdNfsMountEntry 3 }

                  ncdNfsMountEntryServerDir OBJECT-TYPE
                          SYNTAX  OCTET STRING
                          ACCESS  read-only
                          STATUS  optional
                          ::= { ncdNfsMountEntry 4 }

                  ncdNfsMountEntryReadSize OBJECT-TYPE
                          SYNTAX  INTEGER
                          ACCESS  read-write
                          STATUS  optional
                          ::= { ncdNfsMountEntry 5 }

                  ncdNfsMountEntryWriteSize OBJECT-TYPE
                          SYNTAX  INTEGER
                          ACCESS  read-write
                          STATUS  optional
                          ::= { ncdNfsMountEntry 6 }

                  ncdNfsMountEntryRetrans OBJECT-TYPE
                          SYNTAX  INTEGER
                          ACCESS  read-write
                          STATUS  optional
                          ::= { ncdNfsMountEntry 7 }

                  ncdNfsMountEntryTimeout OBJECT-TYPE
                          SYNTAX  TimeTicks
                          ACCESS  read-write
                          STATUS  optional
                          ::= { ncdNfsMountEntry 8 }

		END
