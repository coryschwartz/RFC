--
-- Root of olivetti private MIB, LMS resource MIBs must be added to this file
--

OLIVETTI-MIB { iso org(3) dod(6) internet(1) private(4) enterprises(1) 279 }

DEFINITIONS ::= BEGIN

IMPORTS
        org, dod, internet, private, enterprises, OBJECT-TYPE
            FROM RFC1155-SMI;
olivetti	OBJECT IDENTIFIER ::= { enterprises 279 }
experiments	OBJECT IDENTIFIER ::= { olivetti 1 }
smuxpeersid	OBJECT IDENTIFIER ::= { experiments 2 } 

-- object types

olisysObjectID OBJECT-TYPE
	SYNTAX	DisplayString
	ACCESS	read-only
	STATUS	mandatory
	::= { experiments 1 }

--
-- lms tree starting here
--

lms          OBJECT IDENTIFIER ::= { olivetti 2 }
lms-trap     OBJECT IDENTIFIER ::= { olivetti 3 }

lsx-unix OBJECT IDENTIFIER ::= { lms 6 }

lms-SysName OBJECT-TYPE
	  SYNTAX DisplayString(SIZE(0..17))
	  ACCESS not-accessible
	  STATUS mandatory
	  ::={lms-trap 1}

lms-SubAddress OBJECT-TYPE
	  SYNTAX DisplayString(SIZE(0..17))
	  ACCESS not-accessible
	  STATUS mandatory
	  ::={lms-trap 2}

lms-LogType OBJECT-TYPE
	  SYNTAX DisplayString(SIZE(0..6))
	  ACCESS not-accessible
	  STATUS mandatory
	  ::={lms-trap 3}

lms-FilterType OBJECT-TYPE
	  SYNTAX DisplayString(SIZE(0..10))
	  ACCESS not-accessible
	  STATUS mandatory
	  ::={lms-trap 4}

lms-RecLevel OBJECT-TYPE
	  SYNTAX DisplayString(SIZE(0..4))
	  ACCESS not-accessible
	  STATUS mandatory
	  ::={lms-trap 5}

lms-RecCode OBJECT-TYPE
	  SYNTAX DisplayString(SIZE(0..5))
	  ACCESS not-accessible
	  STATUS mandatory
	  ::={lms-trap 6}

lms-ProductId OBJECT-TYPE
	  SYNTAX DisplayString(SIZE(0..9))
	  ACCESS not-accessible
	  STATUS mandatory
	  ::={lms-trap 7}

lms-Class OBJECT-TYPE
	  SYNTAX DisplayString(SIZE(0..7))
	  ACCESS not-accessible
	  STATUS mandatory
	  ::={lms-trap 8}

lms-SubClass OBJECT-TYPE
	  SYNTAX DisplayString(SIZE(0..9))
	  ACCESS not-accessible
	  STATUS mandatory
	  ::={lms-trap 9}

lms-ResourceName OBJECT-TYPE
	  SYNTAX DisplayString(SIZE(0..15))
	  ACCESS not-accessible
	  STATUS mandatory
	  ::={lms-trap 10}

lms-GenerationDate OBJECT-TYPE
	  SYNTAX DisplayString(SIZE(0..18))
	  ACCESS not-accessible
	  STATUS mandatory
	  ::={lms-trap 11}

lms-LogString OBJECT-TYPE
	  SYNTAX DisplayString(SIZE(0..5000))
	  ACCESS not-accessible
	  STATUS mandatory
	  ::={lms-trap 12}


uxlms-systemrm    OBJECT IDENTIFIER ::= { lsx-unix 7}

uxlms-system      OBJECT IDENTIFIER ::= { uxlms-systemrm 0 }

uxlms-systemrmTable    OBJECT-TYPE
       SYNTAX SEQUENCE OF Uxlms-systemrmEntry
	   ACCESS not-accessible
	   STATUS mandatory
	   ::= { uxlms-system 1 }

uxlms-systemrmEntry    OBJECT-TYPE
       SYNTAX Uxlms-systemrmEntry  
	   ACCESS not-accessible
	   STATUS mandatory
	   ::= { uxlms-systemrmTable 1 }

Uxlms-systemrmEntry ::= SEQUENCE {
                       uxlms-systemrmInstName DisplayString,
                       uxlms-systemrmSubAddr DisplayString
					   }
					   
uxlms-systemrmInstName OBJECT-TYPE
       SYNTAX DisplayString (SIZE(0..14))
	   ACCESS read-only
	   STATUS mandatory
	   ::= { uxlms-systemrmEntry 1 }

uxlms-systemrmSubAddr OBJECT-TYPE
       SYNTAX DisplayString (SIZE(0..14))
	   ACCESS read-only
	   STATUS mandatory
	   ::= { uxlms-systemrmEntry 2 }

-- Trap Definitions

lmstrap   TRAP-TYPE
     ENTERPRISE	olivetti
     VARIABLES	{lms-SysName, lms-SubAddress, lms-LogType, lms-FilterType,
	 lms-RecLevel, lms-RecCode, lms-ProductId, lms-Class, lms-SubClass,
	 lms-ResourceName, lms-GenerationDate, lms-LogString}
	 ::= 138

--
-- lms tree ending here
--
-- UXLMX DEFINITIONS ::= BEGIN
-- 
-- IMPORTS
--     enterprises,OBJECT-TYPE
-- 	    FROM RFC1155-SMI;
-- 
-- 
uxlmx-LM     OBJECT IDENTIFIER ::= { lsx-unix 13}

uxlmx-SRVLM           OBJECT IDENTIFIER ::= { uxlmx-LM 101 }


uxlmx-SRVLMTable    OBJECT-TYPE
       SYNTAX SEQUENCE OF SrvlmEntry
	   ACCESS not-accessible
	   STATUS mandatory
	   ::= { uxlmx-SRVLM 1 }

uxlmx-SRVLMEntry    OBJECT-TYPE
       SYNTAX SrvlmEntry  
	   ACCESS not-accessible
	   STATUS mandatory
	   INDEX { uxlmx-SRVLMSysName,
		   uxlmx-SRVLMInstName,
		   uxlmx-SRVLMSubAddr}
	   ::= { uxlmx-SRVLMTable 1 }

SrvlmEntry ::= SEQUENCE {
                       uxlmx-SRVLMSysName DisplayString,
                       uxlmx-SRVLMInstName DisplayString,
                       uxlmx-SRVLMSubAddr DisplayString,
                       uxlmx-wknumNCBs Counter,
                       uxlmx-wkfiNCBs Counter,
                       uxlmx-wkfcNCBs Counter,
                       uxlmx-wksesstart Counter,
                       uxlmx-wksessfail Counter,
                       uxlmx-wkuses Counter,
                       uxlmx-wkusefail Counter,
                       uxlmx-wkautorec Counter,
                       uxlmx-svfopens Counter,
                       uxlmx-svdevopens Counter,
                       uxlmx-svjobsqueued Counter,
                       uxlmx-svsopens Counter,
                       uxlmx-svstimedout Counter,
                       uxlmx-svserrorout Counter,
                       uxlmx-svpwerrors Counter,
                       uxlmx-svpermerrors Counter,
                       uxlmx-svsyserrors Counter,
                       uxlmx-svbytessent Counter,
                       uxlmx-svbytesrcvd Counter,
                       uxlmx-svavresponse Counter
					   }

uxlmx-SRVLMSysName OBJECT-TYPE
       SYNTAX DisplayString (SIZE(0..16))
	   ACCESS read-only
	   STATUS mandatory
	   ::= { uxlmx-SRVLMEntry 1 }
					   
uxlmx-SRVLMInstName OBJECT-TYPE
       SYNTAX DisplayString (SIZE(0..14))
	   ACCESS read-only
	   STATUS mandatory
	   ::= { uxlmx-SRVLMEntry 2 }

uxlmx-SRVLMSubAddr  OBJECT-TYPE
       SYNTAX DisplayString (SIZE(0..14))
	   ACCESS read-only
	   STATUS mandatory
	   ::= { uxlmx-SRVLMEntry 3 }

uxlmx-wknumNCBs OBJECT-TYPE
       SYNTAX Counter
	   ACCESS read-only
	   STATUS mandatory
	   ::= { uxlmx-SRVLMEntry 4 }

uxlmx-wkfiNCBs OBJECT-TYPE
       SYNTAX Counter
	   ACCESS read-only
	   STATUS mandatory
	   ::= { uxlmx-SRVLMEntry 5 }

uxlmx-wkfcNCBs OBJECT-TYPE
       SYNTAX Counter
	   ACCESS read-only
	   STATUS mandatory
	   ::= { uxlmx-SRVLMEntry 6 }

uxlmx-wksesstart OBJECT-TYPE
       SYNTAX Counter
	   ACCESS read-only
	   STATUS mandatory
	   ::= { uxlmx-SRVLMEntry 7 }

uxlmx-wksessfail OBJECT-TYPE
       SYNTAX Counter
	   ACCESS read-only
	   STATUS mandatory
	   ::= { uxlmx-SRVLMEntry 8 }

uxlmx-wkuses OBJECT-TYPE
       SYNTAX Counter
	   ACCESS read-only
	   STATUS mandatory
	   ::= { uxlmx-SRVLMEntry 9 }

uxlmx-wkusefail OBJECT-TYPE
       SYNTAX Counter
	   ACCESS read-only
	   STATUS mandatory
	   ::= { uxlmx-SRVLMEntry 10 }

uxlmx-wkautorec OBJECT-TYPE
       SYNTAX Counter
	   ACCESS read-only
	   STATUS mandatory
	   ::= { uxlmx-SRVLMEntry 11 }

uxlmx-svfopens OBJECT-TYPE
       SYNTAX Counter
	   ACCESS read-only
	   STATUS mandatory
	   ::= { uxlmx-SRVLMEntry 12 }

uxlmx-svdevopens OBJECT-TYPE
       SYNTAX Counter
	   ACCESS read-only
	   STATUS mandatory
	   ::= { uxlmx-SRVLMEntry 13 }

uxlmx-svjobsqueued OBJECT-TYPE
       SYNTAX Counter
	   ACCESS read-only
	   STATUS mandatory
	   ::= { uxlmx-SRVLMEntry 14 }

uxlmx-svsopens OBJECT-TYPE
       SYNTAX Counter
	   ACCESS read-only
	   STATUS mandatory
	   ::= { uxlmx-SRVLMEntry 15 }

uxlmx-svstimedout OBJECT-TYPE
       SYNTAX Counter
	   ACCESS read-only
	   STATUS mandatory
	   ::= { uxlmx-SRVLMEntry 16 }

uxlmx-svserrorout OBJECT-TYPE
       SYNTAX Counter
	   ACCESS read-only
	   STATUS mandatory
	   ::= { uxlmx-SRVLMEntry 17 }

uxlmx-svpwerrors OBJECT-TYPE
       SYNTAX Counter
	   ACCESS read-only
	   STATUS mandatory
	   ::= { uxlmx-SRVLMEntry 18 }

uxlmx-svpermerrors OBJECT-TYPE
       SYNTAX Counter
	   ACCESS read-only
	   STATUS mandatory
	   ::= { uxlmx-SRVLMEntry 19 }

uxlmx-svsyserrors OBJECT-TYPE
       SYNTAX Counter
	   ACCESS read-only
	   STATUS mandatory
	   ::= { uxlmx-SRVLMEntry 20 }

uxlmx-svbytessent OBJECT-TYPE
       SYNTAX Counter
	   ACCESS read-only
	   STATUS mandatory
	   ::= { uxlmx-SRVLMEntry 21 }

uxlmx-svbytesrcvd OBJECT-TYPE
       SYNTAX Counter
	   ACCESS read-only
	   STATUS mandatory
	   ::= { uxlmx-SRVLMEntry 22 }

uxlmx-svavresponse OBJECT-TYPE
       SYNTAX Counter
	   ACCESS read-only
	   STATUS mandatory
	   ::= { uxlmx-SRVLMEntry 23 }


-- 
-- IMPORTS
--     enterprises,OBJECT-TYPE
-- 	    FROM RFC1155-SMI;
-- 
-- 
uxos-core   	   OBJECT IDENTIFIER ::= { lsx-unix 77}
-- _SSTFIX: was:
-- uxos-disc       OBJECT IDENTIFIER ::= { lsx-unix 68}
uxos-disc          OBJECT IDENTIFIER ::= { lsx-unix 65}

uxos-cpu           OBJECT IDENTIFIER ::= { uxos-core 1 }
-- _OLISOFT - (CV) 24 Set 93 - aligned to the LMS resource file.
uxos-nproc         OBJECT IDENTIFIER ::= { uxos-core 2 }
uxos-ufsfreeinode  OBJECT IDENTIFIER ::= { uxos-core 3 }
uxos-physmem       OBJECT IDENTIFIER ::= { uxos-core 4 }
uxos-filecnt       OBJECT IDENTIFIER ::= { uxos-core 5 }
uxos-boottime      OBJECT IDENTIFIER ::= { uxos-core 6 }
uxos-sysinfo       OBJECT IDENTIFIER ::= { uxos-core 7 }
uxos-minfo         OBJECT IDENTIFIER ::= { uxos-core 8 }
uxos-vminfo        OBJECT IDENTIFIER ::= { uxos-core 9 }
uxos-syserr        OBJECT IDENTIFIER ::= { uxos-core 10 }
uxos-kmeminfo      OBJECT IDENTIFIER ::= { uxos-core 11 }
uxos-rtminfo       OBJECT IDENTIFIER ::= { uxos-core 12 }
uxos-var           OBJECT IDENTIFIER ::= { uxos-core 13 }
uxos-shlbinfo      OBJECT IDENTIFIER ::= { uxos-core 14 }
uxos-flckinfo      OBJECT IDENTIFIER ::= { uxos-core 15 }
uxos-tune          OBJECT IDENTIFIER ::= { uxos-core 16 }
uxos-avenrun       OBJECT IDENTIFIER ::= { uxos-core 17 }
uxos-vmcnt         OBJECT IDENTIFIER ::= { uxos-core 18 }
uxos-vmrate        OBJECT IDENTIFIER ::= { uxos-core 19 }
uxos-vmsum         OBJECT IDENTIFIER ::= { uxos-core 20 }
uxos-vmtotal       OBJECT IDENTIFIER ::= { uxos-core 21 }
uxos-lbolt	   OBJECT IDENTIFIER ::= { uxos-core 22 }
uxos-availsmem     OBJECT IDENTIFIER ::= { uxos-core 23 }
uxos-availrmem     OBJECT IDENTIFIER ::= { uxos-core 24 }
uxos-availkmem     OBJECT IDENTIFIER ::= { uxos-core 25 }
uxos-namecache     OBJECT IDENTIFIER ::= { uxos-core 26 }
uxos-buffercache   OBJECT IDENTIFIER ::= { uxos-core 27 }
-- _OLISOFT
-- (FR) 6 Ago 1993
uxos-aioinfo   	   OBJECT IDENTIFIER ::= { uxos-core 28 }
uxos-lioinfo   	   OBJECT IDENTIFIER ::= { uxos-core 29 }
uxos-ipcinfo   	   OBJECT IDENTIFIER ::= { uxos-core 30 }
uxos-flockinfo 	   OBJECT IDENTIFIER ::= { uxos-core 31 }
uxos-segminfo  	   OBJECT IDENTIFIER ::= { uxos-core 32 }
-- _OLISOFT & CFS - Veritas
-- (FR) 1 Set 1993
uxos-vxinfo  	   OBJECT IDENTIFIER ::= { uxos-core 33 }

-- _SSTFIX: was:
-- uxos-scsi 	   OBJECT IDENTIFIER ::= { uxos-disc 1 }
uxos-scsi 	   OBJECT IDENTIFIER ::= { uxos-disc 0 }

--............................................................................
-- Cpu group
--............................................................................

uxos-cpuTable    OBJECT-TYPE
       SYNTAX SEQUENCE OF CpuEntry
	   ACCESS not-accessible
	   STATUS mandatory
	   ::= { uxos-cpu 1 }

uxos-cpuEntry    OBJECT-TYPE
       SYNTAX CpuEntry  
	   ACCESS not-accessible
	   STATUS mandatory
	   INDEX {uxos-cpuSysName,
		  uxos-cpuInstName,
		  uxos-cpuSubAddr}
	   ::= { uxos-cpuTable 1 }

CpuEntry ::= SEQUENCE {
                       uxos-cpuSysName DisplayString,
                       uxos-cpuInstName DisplayString,
                       uxos-cpuSubAddr DisplayString,
                       uxos-numOfCpu Counter
					   }
uxos-cpuSysName OBJECT-TYPE
       SYNTAX DisplayString (SIZE(0..14))
	   ACCESS read-only
	   STATUS mandatory
	   ::= { uxos-cpuEntry 1 }

uxos-cpuInstName OBJECT-TYPE
       SYNTAX DisplayString (SIZE(0..14))
	   ACCESS read-only
	   STATUS mandatory
	   ::= { uxos-cpuEntry 2 }

uxos-cpuSubAddr  OBJECT-TYPE
       SYNTAX DisplayString (SIZE(0..14))
	   ACCESS read-only
	   STATUS mandatory
	   ::= { uxos-cpuEntry 3 }

uxos-numOfCpu    OBJECT-TYPE
       SYNTAX Counter
	   ACCESS read-only
	   STATUS mandatory
	   ::= { uxos-cpuEntry 4 }

-- _SSTFIX (AV) 24 Set 1992 ..................................................
-- Nproc group
--............................................................................

uxos-nprocTable    OBJECT-TYPE
       SYNTAX SEQUENCE OF NprocEntry
	   ACCESS not-accessible
	   STATUS mandatory
	   ::= { uxos-nproc 1 }

uxos-nprocEntry    OBJECT-TYPE
       SYNTAX NprocEntry  
	   ACCESS not-accessible
	   STATUS mandatory
	   INDEX {uxos-nprocSysName,
		  uxos-nprocInstName,
		  uxos-nprocSubAddr}
	   ::= { uxos-nprocTable 1 }

NprocEntry ::= SEQUENCE {
                       uxos-nprocSysName DisplayString,
                       uxos-nprocInstName DisplayString,
                       uxos-nprocSubAddr DisplayString,
                       uxos-numOfProc Counter
					   }
					   
uxos-nprocSysName OBJECT-TYPE
       SYNTAX DisplayString (SIZE(0..14))
	   ACCESS read-only
	   STATUS mandatory
	   ::= { uxos-nprocEntry 1 }

uxos-nprocInstName OBJECT-TYPE
       SYNTAX DisplayString (SIZE(0..14))
	   ACCESS read-only
	   STATUS mandatory
	   ::= { uxos-nprocEntry 2 }

uxos-nprocSubAddr  OBJECT-TYPE
       SYNTAX DisplayString (SIZE(0..14))
	   ACCESS read-only
	   STATUS mandatory
	   ::= { uxos-nprocEntry 3 }

uxos-numOfProc    OBJECT-TYPE
       SYNTAX Counter
	   ACCESS read-only
	   STATUS mandatory
	   ::= { uxos-nprocEntry 4 }

-- _SSTFIX (AV) 24 Set 1992 ..................................................
-- Ufsfreeinode group
--............................................................................

uxos-ufsfreeinodeTable    OBJECT-TYPE
       SYNTAX SEQUENCE OF UfsfreeinodeEntry
	   ACCESS not-accessible
	   STATUS mandatory
	   ::= { uxos-ufsfreeinode 1 }

uxos-ufsfreeinodeEntry    OBJECT-TYPE
       SYNTAX UfsfreeinodeEntry  
	   ACCESS not-accessible
	   STATUS mandatory
	   INDEX {uxos-ufsfreeinodeSysName,
		  uxos-ufsfreeinodeInstName,
		  uxos-ufsfreeinodeSubAddr}
	   ::= { uxos-ufsfreeinodeTable 1 }

UfsfreeinodeEntry ::= SEQUENCE {
                       uxos-ufsfreeinodeSysName DisplayString,
                       uxos-ufsfreeinodeInstName DisplayString,
                       uxos-ufsfreeinodeSubAddr DisplayString,
                       uxos-numOfUfsfreeinode Counter
					   }
uxos-ufsfreeinodeSysName OBJECT-TYPE
       SYNTAX DisplayString (SIZE(0..14))
	   ACCESS read-only
	   STATUS mandatory
	   ::= { uxos-ufsfreeinodeEntry 1 }

					   
uxos-ufsfreeinodeInstName OBJECT-TYPE
       SYNTAX DisplayString (SIZE(0..14))
	   ACCESS read-only
	   STATUS mandatory
	   ::= { uxos-ufsfreeinodeEntry 2 }

uxos-ufsfreeinodeSubAddr  OBJECT-TYPE
       SYNTAX DisplayString (SIZE(0..14))
	   ACCESS read-only
	   STATUS mandatory
	   ::= { uxos-ufsfreeinodeEntry 3 }

uxos-numOfUfsfreeinode    OBJECT-TYPE
       SYNTAX Counter
	   ACCESS read-only
	   STATUS mandatory
	   ::= { uxos-ufsfreeinodeEntry 4 }

--............................................................................
-- Physmem group
--............................................................................

uxos-memTable    OBJECT-TYPE
       SYNTAX SEQUENCE OF MemEntry
	   ACCESS not-accessible
	   STATUS mandatory
	   ::= { uxos-physmem 1 }

uxos-memEntry    OBJECT-TYPE
       SYNTAX MemEntry  
	   ACCESS not-accessible
	   STATUS mandatory
	   INDEX {uxos-memSysName,
		  uxos-memInstName,
		  uxos-memSubAddr}
	   ::= { uxos-memTable 1 }

MemEntry ::= SEQUENCE {
                       uxos-memSysName DisplayString,
                       uxos-memInstName DisplayString,
                       uxos-memSubAddr DisplayString,
                       uxos-memSize Counter
					   }
uxos-memSysName OBJECT-TYPE
       SYNTAX DisplayString (SIZE(0..14))
	   ACCESS read-only
	   STATUS mandatory
	   ::= { uxos-memEntry 1 }

					   
uxos-memInstName OBJECT-TYPE
       SYNTAX DisplayString (SIZE(0..14))
	   ACCESS read-only
	   STATUS mandatory
	   ::= { uxos-memEntry 2 }

uxos-memSubAddr  OBJECT-TYPE
       SYNTAX DisplayString (SIZE(0..16))
	   ACCESS read-only
	   STATUS mandatory
	   ::= { uxos-memEntry 3 }

uxos-memSize   OBJECT-TYPE
       SYNTAX Counter
	   ACCESS read-only
	   STATUS mandatory
	   ::= { uxos-memEntry 4 }

--............................................................................
-- Filecnt group
--............................................................................

uxos-fileTable OBJECT-TYPE
       SYNTAX SEQUENCE OF FileEntry
	   ACCESS not-accessible
	   STATUS mandatory
	   ::= { uxos-filecnt 1 }

uxos-fileEntry OBJECT-TYPE
       SYNTAX FileEntry  
	   ACCESS not-accessible
	   STATUS mandatory
	   INDEX {uxos-fileSysName,
		  uxos-fileInstName,
		  uxos-fileSubAddr}
	   ::= { uxos-fileTable 1 }

FileEntry ::= SEQUENCE {
                       uxos-fileSysName DisplayString,
                       uxos-fileInstName DisplayString,
                       uxos-fileSubAddr DisplayString,
                       uxos-numOfFile Counter
					   }
uxos-fileSysName OBJECT-TYPE
       SYNTAX DisplayString (SIZE(0..14))
	   ACCESS read-only
	   STATUS mandatory
	   ::= { uxos-fileEntry 1 }
					   
uxos-fileInstName OBJECT-TYPE
       SYNTAX DisplayString (SIZE(0..14))
	   ACCESS read-only
	   STATUS mandatory
	   ::= { uxos-fileEntry 2 }

uxos-fileSubAddr OBJECT-TYPE
       SYNTAX DisplayString (SIZE(0..16))
	   ACCESS read-only
	   STATUS mandatory
	   ::= { uxos-fileEntry 3 }

uxos-numOfFile  OBJECT-TYPE
       SYNTAX Counter
	   ACCESS read-only
	   STATUS mandatory
	   ::= { uxos-fileEntry 4 }

--............................................................................
-- Boottime group
--............................................................................

uxos-bootTable OBJECT-TYPE
       SYNTAX SEQUENCE OF BootEntry
	   ACCESS not-accessible
	   STATUS mandatory
	   ::= { uxos-boottime 1 }

uxos-bootEntry OBJECT-TYPE
       SYNTAX BootEntry  
	   ACCESS not-accessible
	   STATUS mandatory
	   INDEX {uxos-bootSysName,
		  uxos-bootInstName,
		  uxos-bootSubAddr}
	   ::= { uxos-bootTable 1 }

BootEntry ::= SEQUENCE {
                       uxos-bootSysName DisplayString,
                       uxos-bootInstName DisplayString,
                       uxos-bootSubAddr DisplayString,
                       uxos-bootTime Counter
					   }
					   
uxos-bootSysName OBJECT-TYPE
       SYNTAX DisplayString (SIZE(0..14))
	   ACCESS read-only
	   STATUS mandatory
	   ::= { uxos-bootEntry 1 }

uxos-bootInstName OBJECT-TYPE
       SYNTAX DisplayString (SIZE(0..14))
	   ACCESS read-only
	   STATUS mandatory
	   ::= { uxos-bootEntry 2 }

uxos-bootSubAddr  OBJECT-TYPE
       SYNTAX DisplayString (SIZE(0..16))
	   ACCESS read-only
	   STATUS mandatory
	   ::= { uxos-bootEntry 3 }

uxos-bootTime   OBJECT-TYPE
       SYNTAX Counter
	   ACCESS read-only
	   STATUS mandatory
	   ::= { uxos-bootEntry 4 }


 --...................................................................
 -- Lbolt group
 --...................................................................

uxos-lboltTable OBJECT-TYPE
       SYNTAX SEQUENCE OF LboltEntry
	   ACCESS not-accessible
	   STATUS mandatory
	   ::= { uxos-lbolt 1 }

uxos-lboltEntry OBJECT-TYPE
       SYNTAX LboltEntry  
	   ACCESS not-accessible
	   STATUS mandatory
	   INDEX {uxos-lboltSysName,
		  uxos-lboltInstName,
		  uxos-lboltSubAddr}
	   ::= { uxos-lboltTable 1 }

LboltEntry ::= SEQUENCE {
                       uxos-lboltSysName DisplayString,
                       uxos-lboltInstName DisplayString,
                       uxos-lboltSubAddr DisplayString,
                       uxos-numOfTick Counter
					   }
					   
uxos-lboltSysName OBJECT-TYPE
       SYNTAX DisplayString (SIZE(0..14))
	   ACCESS read-only
	   STATUS mandatory
	   ::= { uxos-lboltEntry 1 }

uxos-lboltInstName OBJECT-TYPE
       SYNTAX DisplayString (SIZE(0..14))
	   ACCESS read-only
	   STATUS mandatory
	   ::= { uxos-lboltEntry 2 }

uxos-lboltSubAddr  OBJECT-TYPE
       SYNTAX DisplayString (SIZE(0..16))
	   ACCESS read-only
	   STATUS mandatory
	   ::= { uxos-lboltEntry 3 }

uxos-numOfTick   OBJECT-TYPE
       SYNTAX Counter
	   ACCESS read-only
	   STATUS mandatory
	   ::= { uxos-lboltEntry 4 }


 --...................................................................
 -- Availkmem group
 --...................................................................

uxos-kmemTable OBJECT-TYPE
       SYNTAX SEQUENCE OF KmemEntry
	   ACCESS not-accessible
	   STATUS mandatory
	   ::= { uxos-availkmem 1 }

uxos-kmemEntry OBJECT-TYPE
       SYNTAX KmemEntry  
	   ACCESS not-accessible
	   STATUS mandatory
	   INDEX {uxos-kmemSysName,
		  uxos-kmemInstName,
		  uxos-kmemSubAddr}
	   ::= { uxos-kmemTable 1 }

KmemEntry ::= SEQUENCE {
                       uxos-kmemSysName DisplayString,
                       uxos-kmemInstName DisplayString,
                       uxos-kmemSubAddr DisplayString,
                       uxos-kmemNumOfPages Counter
					   }
					   
uxos-kmemSysName OBJECT-TYPE
       SYNTAX DisplayString (SIZE(0..14))
	   ACCESS read-only
	   STATUS mandatory
	   ::= { uxos-kmemEntry 1 }

uxos-kmemInstName OBJECT-TYPE
       SYNTAX DisplayString (SIZE(0..14))
	   ACCESS read-only
	   STATUS mandatory
	   ::= { uxos-kmemEntry 2 }

uxos-kmemSubAddr  OBJECT-TYPE
       SYNTAX DisplayString (SIZE(0..16))
	   ACCESS read-only
	   STATUS mandatory
	   ::= { uxos-kmemEntry 3 }

uxos-kmemNumOfPages  OBJECT-TYPE
       SYNTAX Counter
	   ACCESS read-only
	   STATUS mandatory
	   ::= { uxos-kmemEntry 4 }


 --...................................................................
 -- Availrmem group
 --...................................................................

uxos-rmemTable OBJECT-TYPE
       SYNTAX SEQUENCE OF RmemEntry
	   ACCESS not-accessible
	   STATUS mandatory
	   ::= { uxos-availrmem 1 }

uxos-rmemEntry OBJECT-TYPE
       SYNTAX RmemEntry  
	   ACCESS not-accessible
	   STATUS mandatory
	   INDEX {uxos-rmemSysName,
		  uxos-rmemInstName,
		  uxos-rmemSubAddr}
	   ::= { uxos-rmemTable 1 }

RmemEntry ::= SEQUENCE {
                       uxos-rmemSysName DisplayString,
                       uxos-rmemInstName DisplayString,
                       uxos-rmemSubAddr DisplayString,
                       uxos-rmemNumOfPages Counter
					   }
					   
uxos-rmemSysName OBJECT-TYPE
       SYNTAX DisplayString (SIZE(0..14))
	   ACCESS read-only
	   STATUS mandatory
	   ::= { uxos-rmemEntry 1 }

uxos-rmemInstName OBJECT-TYPE
       SYNTAX DisplayString (SIZE(0..14))
	   ACCESS read-only
	   STATUS mandatory
	   ::= { uxos-rmemEntry 2 }

uxos-rmemSubAddr  OBJECT-TYPE
       SYNTAX DisplayString (SIZE(0..16))
	   ACCESS read-only
	   STATUS mandatory
	   ::= { uxos-rmemEntry 3 }

uxos-rmemNumOfPages  OBJECT-TYPE
       SYNTAX Counter
	   ACCESS read-only
	   STATUS mandatory
	   ::= { uxos-rmemEntry 4 }


 --...................................................................
 -- Availsmem group
 --...................................................................

uxos-smemTable OBJECT-TYPE
       SYNTAX SEQUENCE OF SmemEntry
	   ACCESS not-accessible
	   STATUS mandatory
	   ::= { uxos-availsmem 1 }

uxos-smemEntry OBJECT-TYPE
       SYNTAX SmemEntry  
	   ACCESS not-accessible
	   STATUS mandatory
	   INDEX {uxos-smemSysName,
		  uxos-smemInstName,
		  uxos-smemSubAddr}
	   ::= { uxos-smemTable 1 }

SmemEntry ::= SEQUENCE {
                       uxos-smemSysName DisplayString,
                       uxos-smemInstName DisplayString,
                       uxos-smemSubAddr DisplayString,
                       uxos-smemNumOfPages Counter
					   }
					   
uxos-smemSysName OBJECT-TYPE
       SYNTAX DisplayString (SIZE(0..14))
	   ACCESS read-only
	   STATUS mandatory
	   ::= { uxos-smemEntry 1 }

uxos-smemInstName OBJECT-TYPE
       SYNTAX DisplayString (SIZE(0..14))
	   ACCESS read-only
	   STATUS mandatory
	   ::= { uxos-smemEntry 2 }

uxos-smemSubAddr  OBJECT-TYPE
       SYNTAX DisplayString (SIZE(0..16))
	   ACCESS read-only
	   STATUS mandatory
	   ::= { uxos-smemEntry 3 }

uxos-smemNumOfPages  OBJECT-TYPE
       SYNTAX Counter
	   ACCESS read-only
	   STATUS mandatory
	   ::= { uxos-smemEntry 4 }


 --...................................................................
 -- Sysinfo group
 --...................................................................

uxos-sysTable OBJECT-TYPE
       SYNTAX SEQUENCE OF SysEntry
	   ACCESS not-accessible
	   STATUS mandatory
	   ::= { uxos-sysinfo 1 }

uxos-sysEntry OBJECT-TYPE
       SYNTAX SysEntry  
	   ACCESS not-accessible
	   STATUS mandatory
	   INDEX {uxos-sysSysName,
		  uxos-sysInstName,
		  uxos-sysSubAddr}
	   ::= { uxos-sysTable 1 }

SysEntry ::= SEQUENCE {
                       uxos-sysSysName DisplayString,
                       uxos-sysInstName DisplayString,
                       uxos-sysSubAddr DisplayString,
                       uxos-cpuIdle   	Counter,
                       uxos-cpuUser	Counter,
                       uxos-cpuKernel	Counter,
                       uxos-cpuWait	Counter,
                       uxos-cpuSxbrk	Counter,
                       uxos-wIo 	Counter,
                       uxos-wSwap	Counter,
                       uxos-wPio	Counter,
                       uxos-bread	Counter,
                       uxos-bwrite	Counter,
                       uxos-lread	Counter,
                       uxos-lwrite	Counter,
		       uxos-phread 	Counter,
                       uxos-phwrite	Counter,
                       uxos-swapin	Counter,
                       uxos-swapout	Counter,
                       uxos-pswapin	Counter,
                       uxos-pswapout	Counter,
                       uxos-pswitch	Counter,
                       uxos-syscall	Counter,
                       uxos-sysread	Counter,
                       uxos-syswrite	Counter,
                       uxos-sysfork	Counter,
                       uxos-sysexec	Counter,
                       uxos-runque	Counter,
                       uxos-runocc	Counter,
                       uxos-swpque	Counter,
                       uxos-swpocc	Counter,
                       uxos-iget	Counter,
                       uxos-namei	Counter,
                       uxos-dirblk	Counter,
                       uxos-readch	Counter,
                       uxos-writech	Counter,
                       uxos-rcvint	Counter,
                       uxos-xmtint	Counter,
		       uxos-mdmint	Counter,
                       uxos-rawch	Counter,
		       uxos-canch	Counter,
                       uxos-outch	Counter,
                       uxos-msg		Counter,
                       uxos-sema	Counter
						}
					   
					   
uxos-sysSysName OBJECT-TYPE
       SYNTAX DisplayString (SIZE(0..14))
	   ACCESS read-only
	   STATUS mandatory
	   ::= { uxos-sysEntry 1 }

uxos-sysInstName OBJECT-TYPE
       SYNTAX DisplayString (SIZE(0..14))
	   ACCESS read-only
	   STATUS mandatory
	   ::= { uxos-sysEntry 2 }

uxos-sysSubAddr  OBJECT-TYPE
       SYNTAX DisplayString (SIZE(0..14))
	   ACCESS read-only
	   STATUS mandatory
	   ::= { uxos-sysEntry 3 }

uxos-cpuIdle OBJECT-TYPE
       SYNTAX Counter
	   ACCESS read-only
	   STATUS mandatory
	   ::= { uxos-sysEntry 4 }
					   
uxos-cpuUser OBJECT-TYPE
       SYNTAX Counter
	   ACCESS read-only
	   STATUS mandatory
	   ::= { uxos-sysEntry 5 }
					   
uxos-cpuKernel OBJECT-TYPE
       SYNTAX Counter
	   ACCESS read-only
	   STATUS mandatory
	   ::= { uxos-sysEntry 6 }
					   
uxos-cpuWait OBJECT-TYPE
       SYNTAX Counter
	   ACCESS read-only
	   STATUS mandatory
	   ::= { uxos-sysEntry 7 }
					   
uxos-cpuSxbrk OBJECT-TYPE
       SYNTAX Counter
	   ACCESS read-only
	   STATUS mandatory
	   ::= { uxos-sysEntry 8 }
					   
uxos-wIo OBJECT-TYPE
       SYNTAX Counter
	   ACCESS read-only
	   STATUS mandatory
	   ::= { uxos-sysEntry 9 }
					   
uxos-wSwap OBJECT-TYPE
       SYNTAX Counter
	   ACCESS read-only
	   STATUS mandatory
	   ::= { uxos-sysEntry 10 }
					   
uxos-wPio OBJECT-TYPE
       SYNTAX Counter
	   ACCESS read-only
	   STATUS mandatory
	   ::= { uxos-sysEntry 11 }
					   
uxos-bread OBJECT-TYPE
       SYNTAX Counter 
	   ACCESS read-only
	   STATUS mandatory
	   ::= { uxos-sysEntry 12 }
					   
uxos-bwrite OBJECT-TYPE
       SYNTAX Counter
	   ACCESS read-only
	   STATUS mandatory
	   ::= { uxos-sysEntry 13 }
					   
uxos-lread OBJECT-TYPE
       SYNTAX Counter
	   ACCESS read-only
	   STATUS mandatory
	   ::= { uxos-sysEntry 14 }
					   
uxos-lwrite OBJECT-TYPE
       SYNTAX Counter
	   ACCESS read-only
	   STATUS mandatory
	   ::= { uxos-sysEntry 15 }
					   
uxos-phread OBJECT-TYPE
       SYNTAX Counter
	   ACCESS read-only
	   STATUS mandatory
	   ::= { uxos-sysEntry 16 }
					   
uxos-phwrite OBJECT-TYPE
       SYNTAX Counter
	   ACCESS read-only
	   STATUS mandatory
	   ::= { uxos-sysEntry 17 }
					   
uxos-swapin OBJECT-TYPE
       SYNTAX Counter
	   ACCESS read-only
	   STATUS mandatory
	   ::= { uxos-sysEntry 18 }
					   
uxos-swapout OBJECT-TYPE
       SYNTAX Counter
	   ACCESS read-only
	   STATUS mandatory
	   ::= { uxos-sysEntry 19 }
					   
uxos-pswapin OBJECT-TYPE
       SYNTAX Counter
	   ACCESS read-only
	   STATUS mandatory
	   ::= { uxos-sysEntry 20 }
					   
uxos-pswapout OBJECT-TYPE
       SYNTAX Counter
	   ACCESS read-only
	   STATUS mandatory
	   ::= { uxos-sysEntry 21 }
					   
uxos-pswitch OBJECT-TYPE
       SYNTAX Counter
	   ACCESS read-only
	   STATUS mandatory
	   ::= { uxos-sysEntry 22 }
					   
uxos-syscall OBJECT-TYPE
       SYNTAX Counter
	   ACCESS read-only
	   STATUS mandatory
	   ::= { uxos-sysEntry 23 }
					   
uxos-sysread OBJECT-TYPE
       SYNTAX Counter
	   ACCESS read-only
	   STATUS mandatory
	   ::= { uxos-sysEntry 24 }
					   
uxos-syswrite OBJECT-TYPE
       SYNTAX Counter
	   ACCESS read-only
	   STATUS mandatory
	   ::= { uxos-sysEntry 25 }
					   
uxos-sysfork OBJECT-TYPE
       SYNTAX Counter
	   ACCESS read-only
	   STATUS mandatory
	   ::= { uxos-sysEntry 26}
					   
uxos-sysexec OBJECT-TYPE
       SYNTAX Counter
	   ACCESS read-only
	   STATUS mandatory
	   ::= { uxos-sysEntry 27 }
					   
uxos-runque OBJECT-TYPE
       SYNTAX Counter
	   ACCESS read-only
	   STATUS mandatory
	   ::= { uxos-sysEntry 28 }
					   
uxos-runocc OBJECT-TYPE
       SYNTAX Counter
	   ACCESS read-only
	   STATUS mandatory
	   ::= { uxos-sysEntry 29 }
					   
uxos-swpque OBJECT-TYPE
       SYNTAX Counter
	   ACCESS read-only
	   STATUS mandatory
	   ::= { uxos-sysEntry 30 }
					   
uxos-swpocc OBJECT-TYPE
       SYNTAX Counter
	   ACCESS read-only
	   STATUS mandatory
	   ::= { uxos-sysEntry 31 }
					   
uxos-iget OBJECT-TYPE
       SYNTAX Counter
	   ACCESS read-only
	   STATUS mandatory
	   ::= { uxos-sysEntry 32 }
					   
uxos-namei OBJECT-TYPE
       SYNTAX Counter
	   ACCESS read-only
	   STATUS mandatory
	   ::= { uxos-sysEntry 33 }
					   
uxos-dirblk OBJECT-TYPE
       SYNTAX Counter
	   ACCESS read-only
	   STATUS mandatory
	   ::= { uxos-sysEntry 34 }
					   
uxos-readch OBJECT-TYPE
       SYNTAX Counter
	   ACCESS read-only
	   STATUS mandatory
	   ::= { uxos-sysEntry 35 }
					   
uxos-writech OBJECT-TYPE
       SYNTAX Counter
	   ACCESS read-only
	   STATUS mandatory
	   ::= { uxos-sysEntry 36 }
					   
uxos-rcvint OBJECT-TYPE
       SYNTAX Counter
	   ACCESS read-only
	   STATUS mandatory
	   ::= { uxos-sysEntry 37 }
					   
uxos-xmtint OBJECT-TYPE
       SYNTAX Counter
	   ACCESS read-only
	   STATUS mandatory
	   ::= { uxos-sysEntry 38 }
					   
uxos-mdmint OBJECT-TYPE
       SYNTAX Counter
	   ACCESS not-accessible
	   STATUS mandatory
	   ::= { uxos-sysEntry 39 }
					   
uxos-rawch OBJECT-TYPE
       SYNTAX Counter
	   ACCESS read-only
	   STATUS mandatory
	   ::= { uxos-sysEntry 40 }
					   
uxos-canch OBJECT-TYPE
       SYNTAX Counter
	   ACCESS not-accessible
	   STATUS mandatory
	   ::= { uxos-sysEntry 41 }
					   
uxos-outch OBJECT-TYPE
       SYNTAX Counter
	   ACCESS read-only
	   STATUS mandatory
	   ::= { uxos-sysEntry 42 }
					   
uxos-msg OBJECT-TYPE
       SYNTAX Counter
	   ACCESS read-only
	   STATUS mandatory
	   ::= { uxos-sysEntry 43 }
					   
uxos-sema OBJECT-TYPE
       SYNTAX Counter
	   ACCESS read-only
	   STATUS mandatory
	   ::= { uxos-sysEntry 44 }


 --...................................................................
 -- Minfo group
 --...................................................................

uxos-minfoTable OBJECT-TYPE
       SYNTAX SEQUENCE OF MinfoEntry
	   ACCESS not-accessible
	   STATUS mandatory
	   ::= { uxos-minfo 1 }

uxos-minfoEntry OBJECT-TYPE
       SYNTAX MinfoEntry  
	   ACCESS not-accessible
	   STATUS mandatory
	   INDEX {uxos-minfoSysName,
		  uxos-minfoInstName,
		  uxos-minfoSubAddr}
	   ::= { uxos-minfoTable 1 }

MinfoEntry ::= SEQUENCE {
                       uxos-minfoSysName DisplayString,
                       uxos-minfoInstName 	DisplayString,
                       uxos-minfoSubAddr 	DisplayString,
                       uxos-freememLeast   	Counter,
                       uxos-freememMost   	Counter,
                       uxos-freeswap   		Counter,
                       uxos-sumvfault  		Counter,
                       uxos-demand 		Counter,
                       uxos-swap  		Counter,
                       uxos-cache  		Counter,
                       uxos-file  		Counter,
                       uxos-pfault  		Counter,
                       uxos-cw  		Counter,
                       uxos-steal  		Counter,
                       uxos-freedpgs  		Counter,
		       uxos-vfpg		Counter,
		       uxos-sfpg		Counter,
		       uxos-vspg		Counter,
		       uxos-sspg		Counter,
                       uxos-unmodsw  		Counter,
                       uxos-unmodfl  		Counter,
		       uxos-psoutok		Counter,
		       uxos-psinfail		Counter,
		       uxos-psinok		Counter,
		       uxos-rsout		Counter,
		       uxos-rsin		Counter,
		       uxos-shmem		Counter
						}
					   
					   
uxos-minfoSysName OBJECT-TYPE
       SYNTAX DisplayString (SIZE(0..14))
	   ACCESS read-only
	   STATUS mandatory
	   ::= { uxos-minfoEntry 1 }

uxos-minfoInstName OBJECT-TYPE
       SYNTAX DisplayString (SIZE(0..14))
	   ACCESS read-only
	   STATUS mandatory
	   ::= { uxos-minfoEntry 2 }

uxos-minfoSubAddr  OBJECT-TYPE
       SYNTAX DisplayString (SIZE(0..14))
	   ACCESS read-only
	   STATUS mandatory
	   ::= { uxos-minfoEntry 3 }

uxos-freememLeast OBJECT-TYPE
       SYNTAX Counter
	   ACCESS read-only
	   STATUS mandatory
	   ::= { uxos-minfoEntry 4 }
					   
uxos-freememMost OBJECT-TYPE
       SYNTAX Counter
	   ACCESS read-only
	   STATUS mandatory
	   ::= { uxos-minfoEntry 5 }
					   
uxos-freeswap OBJECT-TYPE
       SYNTAX Counter
	   ACCESS read-only
	   STATUS mandatory
	   ::= { uxos-minfoEntry 6 }
					   
-- _SSTFIX: was:
-- uxos-vfault OBJECT-TYPE
uxos-sumvfault OBJECT-TYPE
       SYNTAX Counter
	   ACCESS read-only
	   STATUS mandatory
	   ::= { uxos-minfoEntry 7 }
					   
uxos-demand OBJECT-TYPE
       SYNTAX Counter
	   ACCESS read-only
	   STATUS mandatory
	   ::= { uxos-minfoEntry 8 }
					   
uxos-swap OBJECT-TYPE
       SYNTAX Counter
	   ACCESS read-only
	   STATUS mandatory
	   ::= { uxos-minfoEntry 9 }
					   
uxos-cache OBJECT-TYPE
       SYNTAX Counter
	   ACCESS read-only
	   STATUS mandatory
	   ::= { uxos-minfoEntry 10 }
					   
uxos-file OBJECT-TYPE
       SYNTAX Counter
	   ACCESS read-only
	   STATUS mandatory
	   ::= { uxos-minfoEntry 11 }
					   
uxos-pfault OBJECT-TYPE
       SYNTAX Counter
	   ACCESS read-only
	   STATUS mandatory
	   ::= { uxos-minfoEntry 12 }
					   
uxos-cw OBJECT-TYPE
       SYNTAX Counter
	   ACCESS read-only
	   STATUS mandatory
	   ::= { uxos-minfoEntry 13 }
					   
uxos-steal OBJECT-TYPE
       SYNTAX Counter
	   ACCESS read-only
	   STATUS mandatory
	   ::= { uxos-minfoEntry 14 }
					   
uxos-freedpgs OBJECT-TYPE
       SYNTAX Counter
	   ACCESS read-only
	   STATUS mandatory
	   ::= { uxos-minfoEntry 15 }
					   
uxos-vfpg OBJECT-TYPE
       SYNTAX Counter
	   ACCESS not-accessible
	   STATUS mandatory
	   ::= { uxos-minfoEntry 16 }
					   
uxos-sfpg OBJECT-TYPE
       SYNTAX Counter
	   ACCESS not-accessible
	   STATUS mandatory
	   ::= { uxos-minfoEntry 17 }
					   
uxos-vspg OBJECT-TYPE
       SYNTAX Counter
	   ACCESS not-accessible
	   STATUS mandatory
	   ::= { uxos-minfoEntry 18 }
					   
uxos-sspg OBJECT-TYPE
       SYNTAX Counter
	   ACCESS not-accessible
	   STATUS mandatory
	   ::= { uxos-minfoEntry 19 }
					   
uxos-unmodsw OBJECT-TYPE
       SYNTAX Counter
	   ACCESS read-only
	   STATUS mandatory
	   ::= { uxos-minfoEntry 20 }
					   
uxos-unmodfl OBJECT-TYPE
       SYNTAX Counter
	   ACCESS read-only
	   STATUS mandatory
	   ::= { uxos-minfoEntry 21 }
					   
uxos-psoutok OBJECT-TYPE
       SYNTAX Counter
	   ACCESS not-accessible
	   STATUS mandatory
	   ::= { uxos-minfoEntry 22 }
					   
uxos-psinfail OBJECT-TYPE
       SYNTAX Counter
	   ACCESS not-accessible
	   STATUS mandatory
	   ::= { uxos-minfoEntry 23 }
					   
uxos-psinok OBJECT-TYPE
       SYNTAX Counter
	   ACCESS not-accessible
	   STATUS mandatory
	   ::= { uxos-minfoEntry 24 }
					   
uxos-rsout OBJECT-TYPE
       SYNTAX Counter
	   ACCESS not-accessible
	   STATUS mandatory
	   ::= { uxos-minfoEntry 25 }
					   
uxos-rsin OBJECT-TYPE
       SYNTAX Counter
	   ACCESS not-accessible
	   STATUS mandatory
	   ::= { uxos-minfoEntry 26 }
					   
uxos-shmem OBJECT-TYPE
       SYNTAX Counter
	   ACCESS not-accessible
	   STATUS mandatory
	   ::= { uxos-minfoEntry 27 }


 --...................................................................
 -- Vminfo group
 --...................................................................

uxos-vminfoTable OBJECT-TYPE
       SYNTAX SEQUENCE OF VminfoEntry
	   ACCESS not-accessible
	   STATUS mandatory
	   ::= { uxos-vminfo 1 }

uxos-vminfoEntry OBJECT-TYPE
       SYNTAX VminfoEntry  
	   ACCESS not-accessible
	   STATUS mandatory
	   INDEX {uxos-vminfoSysName,
		  uxos-vminfoInstName,
		  uxos-vminfoSubAddr}
	   ::= { uxos-vminfoTable 1 }

VminfoEntry ::= SEQUENCE {
                       uxos-vminfoSysName DisplayString,
-- _SSTFIX: was:
-- 		       uxos-vinfoInstName 	DisplayString,
-- 		       uxos-vinfoSubAddr 	DisplayString,
                       uxos-vminfoInstName 	DisplayString,
                       uxos-vminfoSubAddr 	DisplayString,
                       uxos-vPgrec  		Counter,
                       uxos-vXsfrec  		Counter,
                       uxos-vXifrec  		Counter,
                       uxos-vPgin  		Counter,
                       uxos-vPgpgin  		Counter,
                       uxos-vPgout  		Counter,
                       uxos-vPgpgout  		Counter,
                       uxos-vSwpout  		Counter,
                       uxos-vPswpout  		Counter,
                       uxos-vSwpin  		Counter,
                       uxos-vPswpin  		Counter,
                       uxos-vDfree  		Counter,
                       uxos-vScan  		Counter,
                       uxos-vPfault  		Counter,
                       uxos-vVfault  		Counter,
                       uxos-vSftlock  		Counter
						}
					   
					   
uxos-vminfoSysName OBJECT-TYPE
       SYNTAX DisplayString (SIZE(0..14))
	   ACCESS read-only
	   STATUS mandatory
	   ::= { uxos-vminfoEntry 1 }

uxos-vminfoInstName OBJECT-TYPE
       SYNTAX DisplayString (SIZE(0..14))
	   ACCESS read-only
	   STATUS mandatory
	   ::= { uxos-vminfoEntry 2 }

uxos-vminfoSubAddr  OBJECT-TYPE
       SYNTAX DisplayString (SIZE(0..14))
	   ACCESS read-only
	   STATUS mandatory
	   ::= { uxos-vminfoEntry 3 }

uxos-vPgrec OBJECT-TYPE
       SYNTAX Counter
	   ACCESS read-only
	   STATUS mandatory
	   ::= { uxos-vminfoEntry 4 }
					   
uxos-vXsfrec OBJECT-TYPE
       SYNTAX Counter
	   ACCESS read-only
	   STATUS mandatory
	   ::= { uxos-vminfoEntry 5 }
					   
uxos-vXifrec OBJECT-TYPE
       SYNTAX Counter
	   ACCESS read-only
	   STATUS mandatory
	   ::= { uxos-vminfoEntry 6 }
					   
uxos-vPgin OBJECT-TYPE
       SYNTAX Counter
	   ACCESS read-only
	   STATUS mandatory
	   ::= { uxos-vminfoEntry 7 }
					   
uxos-vPgpgin OBJECT-TYPE
       SYNTAX Counter
	   ACCESS read-only
	   STATUS mandatory
	   ::= { uxos-vminfoEntry 8 }
					   
uxos-vPgout OBJECT-TYPE
       SYNTAX Counter
	   ACCESS read-only
	   STATUS mandatory
	   ::= { uxos-vminfoEntry 9 }
					   
uxos-vPgpgout OBJECT-TYPE
       SYNTAX Counter
	   ACCESS read-only
	   STATUS mandatory
	   ::= { uxos-vminfoEntry 10 }
					   
uxos-vSwpout OBJECT-TYPE
       SYNTAX Counter
	   ACCESS read-only
	   STATUS mandatory
	   ::= { uxos-vminfoEntry 11 }
					   
uxos-vPswpout OBJECT-TYPE
       SYNTAX Counter
	   ACCESS read-only
	   STATUS mandatory
	   ::= { uxos-vminfoEntry 12 }
					   
uxos-vSwpin OBJECT-TYPE
       SYNTAX Counter
	   ACCESS read-only
	   STATUS mandatory
	   ::= { uxos-vminfoEntry 13 }
					   
uxos-vPswpin OBJECT-TYPE
       SYNTAX Counter
	   ACCESS read-only
	   STATUS mandatory
	   ::= { uxos-vminfoEntry 14 }
					   
uxos-vDfree OBJECT-TYPE
       SYNTAX Counter
	   ACCESS read-only
	   STATUS mandatory
	   ::= { uxos-vminfoEntry 15 }
					   
uxos-vScan OBJECT-TYPE
       SYNTAX Counter
	   ACCESS read-only
	   STATUS mandatory
	   ::= { uxos-vminfoEntry 16 }
					   
uxos-vPfault OBJECT-TYPE
       SYNTAX Counter
	   ACCESS read-only
	   STATUS mandatory
	   ::= { uxos-vminfoEntry 17 }
					   
uxos-vVfault OBJECT-TYPE
       SYNTAX Counter
	   ACCESS read-only
	   STATUS mandatory
	   ::= { uxos-vminfoEntry 18 }
					   
uxos-vSftlock OBJECT-TYPE
       SYNTAX Counter
	   ACCESS read-only
	   STATUS mandatory
	   ::= { uxos-vminfoEntry 19 }


 --...................................................................
 -- Syserr group
 --...................................................................

uxos-syserrTable OBJECT-TYPE
       SYNTAX SEQUENCE OF SyserrEntry
	   ACCESS not-accessible
	   STATUS mandatory
	   ::= { uxos-syserr 1 }

uxos-syserrEntry OBJECT-TYPE
       SYNTAX SyserrEntry  
	   ACCESS not-accessible
	   STATUS mandatory
	   INDEX {uxos-syserrSysName,
		  uxos-syserrInstName,
		  uxos-syserrSubAddr}
	   ::= { uxos-syserrTable 1 }

SyserrEntry ::= SEQUENCE {
                       uxos-syserrSysName	DisplayString,
                       uxos-syserrInstName 	DisplayString,
                       uxos-syserrSubAddr 	DisplayString,
                       uxos-inodeovf   		Counter,
                       uxos-ufsinodeovf		Counter,
                       uxos-fileovf   		Counter,
                       uxos-textovf   		Counter,
                       uxos-procovf   		Counter
						}
					   
					   
uxos-syserrSysName OBJECT-TYPE
       SYNTAX DisplayString (SIZE(0..14))
	   ACCESS read-only
	   STATUS mandatory
	   ::= { uxos-syserrEntry 1 }

uxos-syserrInstName OBJECT-TYPE
       SYNTAX DisplayString (SIZE(0..14))
	   ACCESS read-only
	   STATUS mandatory
	   ::= { uxos-syserrEntry 2 }

uxos-syserrSubAddr  OBJECT-TYPE
       SYNTAX DisplayString (SIZE(0..14))
	   ACCESS read-only
	   STATUS mandatory
	   ::= { uxos-syserrEntry 3 }

uxos-inodeovf OBJECT-TYPE
       SYNTAX Counter
	   ACCESS read-only
	   STATUS mandatory
	   ::= { uxos-syserrEntry 4 }
					   
uxos-ufsinodeovf OBJECT-TYPE
       SYNTAX Counter
	   ACCESS read-only
	   STATUS mandatory
	   ::= { uxos-syserrEntry 5 }
					   
uxos-fileovf OBJECT-TYPE
       SYNTAX Counter
	   ACCESS read-only
	   STATUS mandatory
	   ::= { uxos-syserrEntry 6 }
					   
uxos-textovf OBJECT-TYPE
       SYNTAX Counter
	   ACCESS not-accessible
	   STATUS mandatory
	   ::= { uxos-syserrEntry 7 }
					   
uxos-procovf OBJECT-TYPE
       SYNTAX Counter
	   ACCESS read-only
	   STATUS mandatory
	   ::= { uxos-syserrEntry 8 }


 --...................................................................
 -- Kmeminfo group
 --...................................................................

uxos-kmeminfoTable OBJECT-TYPE
       SYNTAX SEQUENCE OF KmeminfoEntry
	   ACCESS not-accessible
	   STATUS mandatory
	   ::= { uxos-kmeminfo 1 }

uxos-kmeminfoEntry OBJECT-TYPE
       SYNTAX KmeminfoEntry  
	   ACCESS not-accessible
	   STATUS mandatory
	   INDEX {uxos-kmeminfoSysName,
		  uxos-kmeminfoInstName,
		  uxos-kmeminfoSubAddr}
	   ::= { uxos-kmeminfoTable 1 }

KmeminfoEntry ::= SEQUENCE {
                        uxos-kmeminfoSysName 	DisplayString,
                       	uxos-kmeminfoInstName 	DisplayString,
                       	uxos-kmeminfoSubAddr 	DisplayString,
			uxos-smlMem		Counter,
			uxos-smlAlloc		Counter,
			uxos-smlFail		Counter,
			uxos-lgMem		Counter,
			uxos-lgAlloc		Counter,
			uxos-lgFail		Counter,
			uxos-ovszMem		Counter,
			uxos-ovszAlloc		Counter,
			uxos-ovszFail		Counter
						}
					   
					   
uxos-kmeminfoSysName OBJECT-TYPE
       SYNTAX DisplayString (SIZE(0..14))
	   ACCESS read-only
	   STATUS mandatory
	   ::= { uxos-kmeminfoEntry 1 }

uxos-kmeminfoInstName OBJECT-TYPE
       SYNTAX DisplayString (SIZE(0..14))
	   ACCESS read-only
	   STATUS mandatory
	   ::= { uxos-kmeminfoEntry 2 }

uxos-kmeminfoSubAddr  OBJECT-TYPE
       SYNTAX DisplayString (SIZE(0..14))
	   ACCESS read-only
	   STATUS mandatory
	   ::= { uxos-kmeminfoEntry 3 }

uxos-smlMem OBJECT-TYPE
       SYNTAX Counter
	   ACCESS read-only
	   STATUS mandatory
	   ::= { uxos-kmeminfoEntry 4 }
					   
uxos-smlAlloc OBJECT-TYPE
       SYNTAX Counter
	   ACCESS read-only
	   STATUS mandatory
	   ::= { uxos-kmeminfoEntry 5 }
					   
uxos-smlFail OBJECT-TYPE
       SYNTAX Counter
	   ACCESS read-only
	   STATUS mandatory
	   ::= { uxos-kmeminfoEntry 6 }
					   
uxos-lgMem OBJECT-TYPE
       SYNTAX Counter
	   ACCESS read-only
	   STATUS mandatory
	   ::= { uxos-kmeminfoEntry 7 }
					   
uxos-lgAlloc OBJECT-TYPE
       SYNTAX Counter
	   ACCESS read-only
	   STATUS mandatory
	   ::= { uxos-kmeminfoEntry 8 }
					   
uxos-lgFail OBJECT-TYPE
       SYNTAX Counter
	   ACCESS read-only
	   STATUS mandatory
	   ::= { uxos-kmeminfoEntry 9 }
					   
uxos-ovszMem OBJECT-TYPE
       SYNTAX Counter
	   ACCESS read-only
	   STATUS mandatory
	   ::= { uxos-kmeminfoEntry 10 }
					   
uxos-ovszAlloc OBJECT-TYPE
       SYNTAX Counter
	   ACCESS read-only
	   STATUS mandatory
	   ::= { uxos-kmeminfoEntry 11 }
					   
uxos-ovszFail OBJECT-TYPE
       SYNTAX Counter
	   ACCESS read-only
	   STATUS mandatory
	   ::= { uxos-kmeminfoEntry 12 }


 --...................................................................
 -- Rtminfo group
 --...................................................................

uxos-rtminfoTable OBJECT-TYPE
       SYNTAX SEQUENCE OF RtminfoEntry
	   ACCESS not-accessible
	   STATUS mandatory
	   ::= { uxos-rtminfo 1 }

uxos-rtminfoEntry OBJECT-TYPE
       SYNTAX RtminfoEntry  
	   ACCESS not-accessible
	   STATUS mandatory
	   INDEX {uxos-rtminfoSysName,
		  uxos-rtminfoInstName,
		  uxos-rtminfoSubAddr}
	   ::= { uxos-rtminfoTable 1 }

RtminfoEntry ::= SEQUENCE {
                        uxos-rtminfoSysName 	DisplayString,
                       	uxos-rtminfoInstName 	DisplayString,
                       	uxos-rtminfoSubAddr 	DisplayString,
			uxos-evPost		Counter,
			uxos-evPoll		Counter,
			uxos-evTrap		Counter
						}
					   
					   
uxos-rtminfoSysName OBJECT-TYPE
       SYNTAX DisplayString (SIZE(0..14))
	   ACCESS read-only
	   STATUS mandatory
	   ::= { uxos-rtminfoEntry 1 }

uxos-rtminfoInstName OBJECT-TYPE
       SYNTAX DisplayString (SIZE(0..14))
	   ACCESS read-only
	   STATUS mandatory
	   ::= { uxos-rtminfoEntry 2 }

uxos-rtminfoSubAddr  OBJECT-TYPE
       SYNTAX DisplayString (SIZE(0..14))
	   ACCESS read-only
	   STATUS mandatory
	   ::= { uxos-rtminfoEntry 3 }

uxos-evPost OBJECT-TYPE
       SYNTAX Counter
	   ACCESS read-only
	   STATUS mandatory
	   ::= { uxos-rtminfoEntry 4 }
					   
uxos-evPoll OBJECT-TYPE
       SYNTAX Counter
	   ACCESS read-only
	   STATUS mandatory
	   ::= { uxos-rtminfoEntry 5 }
					   
uxos-evTrap OBJECT-TYPE
       SYNTAX Counter
	   ACCESS read-only
	   STATUS mandatory
	   ::= { uxos-rtminfoEntry 6 }

--.....................................................................
-- Var group
--.....................................................................

uxos-varTable OBJECT-TYPE
       SYNTAX SEQUENCE OF VarEntry
	   ACCESS not-accessible
	   STATUS mandatory
	   ::= { uxos-var 1 }

uxos-varEntry OBJECT-TYPE
       SYNTAX VarEntry  
	   ACCESS not-accessible
	   STATUS mandatory
	   INDEX {uxos-varSysName,
		  uxos-varInstName,
		  uxos-varSubAddr}
	   ::= { uxos-varTable 1 }

VarEntry ::= SEQUENCE {
                        uxos-varSysName 	DisplayString,
                       	uxos-varInstName 	DisplayString,
                       	uxos-varSubAddr 	DisplayString,
			uxos-vBuf		Counter,
			uxos-vCall		Counter,
			uxos-vProc		Counter,
			uxos-vFiller		Counter,
			uxos-vNglobpris		Counter,
			uxos-vMaxsyspri		Counter,
			uxos-vClist		Counter,
			uxos-vMaxup		Counter,
			uxos-vHbuf		Counter,
			uxos-vHmask		Counter,
			uxos-vPbuf		Counter,
			uxos-vSptmap		Counter,
			uxos-vMaxpmem		Counter,
			uxos-vAutoup		Counter,
			uxos-vBufhwm		Counter,
			uxos-vScrn		Counter,
			uxos-vEmap		Counter,
			uxos-vSxt		Counter,
			uxos-vXsdsegs		Counter,
			uxos-vXsdslots		Counter,
			uxos-vPhash		Counter
						}
					   
					   
uxos-varSysName OBJECT-TYPE
       SYNTAX DisplayString (SIZE(0..14))
	   ACCESS read-only
	   STATUS mandatory
	   ::= { uxos-varEntry 1 }

uxos-varInstName OBJECT-TYPE
       SYNTAX DisplayString (SIZE(0..14))
	   ACCESS read-only
	   STATUS mandatory
	   ::= { uxos-varEntry 2 }

uxos-varSubAddr  OBJECT-TYPE
       SYNTAX DisplayString (SIZE(0..14))
	   ACCESS read-only
	   STATUS mandatory
	   ::= { uxos-varEntry 3 }

uxos-vBuf OBJECT-TYPE
       SYNTAX Counter
	   ACCESS read-only
	   STATUS mandatory
	   ::= { uxos-varEntry 4 }
					   
uxos-vCall OBJECT-TYPE
       SYNTAX Counter
	   ACCESS read-only
	   STATUS mandatory
	   ::= { uxos-varEntry 5 }
					   
uxos-vProc OBJECT-TYPE
       SYNTAX Counter
	   ACCESS read-only
	   STATUS mandatory
	   ::= { uxos-varEntry 6 }
					   
uxos-vFiller OBJECT-TYPE
       SYNTAX Counter
	   ACCESS not-accessible
	   STATUS mandatory
	   ::= { uxos-varEntry 7 }
					   
uxos-vNglobpris OBJECT-TYPE
       SYNTAX Counter
	   ACCESS read-only
	   STATUS mandatory
	   ::= { uxos-varEntry 8 }
					   
uxos-vMaxsyspri OBJECT-TYPE
       SYNTAX Counter
	   ACCESS read-only
	   STATUS mandatory
	   ::= { uxos-varEntry 9 }
					   
uxos-vClist OBJECT-TYPE
       SYNTAX Counter
	   ACCESS read-only
	   STATUS mandatory
	   ::= { uxos-varEntry 10 }
					   
uxos-vMaxup OBJECT-TYPE
       SYNTAX Counter
	   ACCESS read-only
	   STATUS mandatory
	   ::= { uxos-varEntry 11 }
					   
uxos-vHbuf OBJECT-TYPE
       SYNTAX Counter
	   ACCESS read-only
	   STATUS mandatory
	   ::= { uxos-varEntry 12 }
					   
uxos-vHmask OBJECT-TYPE
       SYNTAX Counter
	   ACCESS read-only
	   STATUS mandatory
	   ::= { uxos-varEntry 13 }
					   
uxos-vPbuf OBJECT-TYPE
       SYNTAX Counter
	   ACCESS read-only
	   STATUS mandatory
	   ::= { uxos-varEntry 14 }
					   
uxos-vSptmap OBJECT-TYPE
       SYNTAX Counter
	   ACCESS read-only
	   STATUS mandatory
	   ::= { uxos-varEntry 15 }
					   
uxos-vMaxpmem OBJECT-TYPE
       SYNTAX Counter
	   ACCESS read-only
	   STATUS mandatory
	   ::= { uxos-varEntry 16 }
					   
uxos-vAutoup OBJECT-TYPE
       SYNTAX Counter
	   ACCESS read-only
	   STATUS mandatory
	   ::= { uxos-varEntry 17 }
					   
uxos-vBufhwm OBJECT-TYPE
       SYNTAX Counter
	   ACCESS read-only
	   STATUS mandatory
	   ::= { uxos-varEntry 18 }
					   
uxos-vScrn OBJECT-TYPE
       SYNTAX Counter
	   ACCESS read-only
	   STATUS mandatory
	   ::= { uxos-varEntry 19 }
					   
uxos-vEmap OBJECT-TYPE
       SYNTAX Counter
	   ACCESS read-only
	   STATUS mandatory
	   ::= { uxos-varEntry 20 }
					   
uxos-vSxt OBJECT-TYPE
       SYNTAX Counter
	   ACCESS read-only
	   STATUS mandatory
	   ::= { uxos-varEntry 21 }
					   
uxos-vXsdsegs OBJECT-TYPE
       SYNTAX Counter
	   ACCESS read-only
	   STATUS mandatory
	   ::= { uxos-varEntry 22 }
					   
uxos-vXsdslots OBJECT-TYPE
       SYNTAX Counter
	   ACCESS read-only
	   STATUS mandatory
	   ::= { uxos-varEntry 23 }
					   
uxos-vPhash OBJECT-TYPE
       SYNTAX Counter
	   ACCESS read-only
	   STATUS mandatory
	   ::= { uxos-varEntry 24 }


 --...................................................................
 -- Shlbinfo group
 --...................................................................

uxos-shlbinfoTable OBJECT-TYPE
       SYNTAX SEQUENCE OF ShlbinfoEntry
	   ACCESS not-accessible
	   STATUS mandatory
	   ::= { uxos-shlbinfo 1 }

uxos-shlbinfoEntry OBJECT-TYPE
       SYNTAX ShlbinfoEntry  
	   ACCESS not-accessible
	   STATUS mandatory
	   INDEX {uxos-shlbinfoSysName,
		  uxos-shlbinfoInstName,
		  uxos-shlbinfoSubAddr}
	   ::= { uxos-shlbinfoTable 1 }

ShlbinfoEntry ::= SEQUENCE {
                        uxos-shlbinfoSysName 	DisplayString,
                       	uxos-shlbinfoInstName 	DisplayString,
                       	uxos-shlbinfoSubAddr 	DisplayString,
			uxos-shlbs		Counter,
			uxos-shlblnks		Counter,
			uxos-shlbovf		Counter,
			uxos-shlbatts		Counter
						}
					   
uxos-shlbinfoSysName OBJECT-TYPE
       SYNTAX DisplayString (SIZE(0..14))
	   ACCESS read-only
	   STATUS mandatory
	   ::= { uxos-shlbinfoEntry 1 }
					   
-- _SSTFIX: was:
-- uxos-shlbInstName  OBJECT-TYPE
uxos-shlbinfoInstName OBJECT-TYPE
       SYNTAX DisplayString (SIZE(0..14))
	   ACCESS read-only
	   STATUS mandatory
	   ::= { uxos-shlbinfoEntry 2 }

-- _SSTFIX: was:
-- uxos-shlbSubAddr   OBJECT-TYPE
uxos-shlbinfoSubAddr  OBJECT-TYPE
       SYNTAX DisplayString (SIZE(0..14))
	   ACCESS read-only
	   STATUS mandatory
	   ::= { uxos-shlbinfoEntry 3 }

uxos-shlbs OBJECT-TYPE
       SYNTAX Counter
	   ACCESS read-only
	   STATUS mandatory
	   ::= { uxos-shlbinfoEntry 4 }
					   
uxos-shlblnks OBJECT-TYPE
       SYNTAX Counter
	   ACCESS read-only
	   STATUS mandatory
	   ::= { uxos-shlbinfoEntry 5 }
					   
uxos-shlbovf OBJECT-TYPE
       SYNTAX Counter
	   ACCESS read-only
	   STATUS mandatory
	   ::= { uxos-shlbinfoEntry 6 }
					   
uxos-shlbatts OBJECT-TYPE
       SYNTAX Counter
	   ACCESS read-only
	   STATUS mandatory
	   ::= { uxos-shlbinfoEntry 7 }


 --...................................................................
 -- Flckinfo group
 --...................................................................

uxos-flckinfoTable OBJECT-TYPE
       SYNTAX SEQUENCE OF FlckinfoEntry
	   ACCESS not-accessible
	   STATUS mandatory
	   ::= { uxos-flckinfo 1 }

uxos-flckinfoEntry OBJECT-TYPE
       SYNTAX FlckinfoEntry  
	   ACCESS not-accessible
	   STATUS mandatory
	   INDEX {uxos-flckinfoSysName,
		  uxos-flckinfoInstName,
		  uxos-flckinfoSubAddr}
	   ::= { uxos-flckinfoTable 1 }

FlckinfoEntry ::= SEQUENCE {
                        uxos-flckinfoSysName 	DisplayString,
                       	uxos-flckinfoInstName 	DisplayString,
                       	uxos-flckinfoSubAddr 	DisplayString,
			uxos-reccnt		Counter,
			uxos-rectot		Counter
						}
					   
					   
uxos-flckinfoSysName OBJECT-TYPE
       SYNTAX DisplayString (SIZE(0..14))
	   ACCESS read-only
	   STATUS mandatory
	   ::= { uxos-flckinfoEntry 1 }

uxos-flckinfoInstName OBJECT-TYPE
       SYNTAX DisplayString (SIZE(0..14))
	   ACCESS read-only
	   STATUS mandatory
	   ::= { uxos-flckinfoEntry 2 }

uxos-flckinfoSubAddr  OBJECT-TYPE
       SYNTAX DisplayString (SIZE(0..14))
	   ACCESS read-only
	   STATUS mandatory
	   ::= { uxos-flckinfoEntry 3 }

uxos-reccnt OBJECT-TYPE
       SYNTAX Counter
	   ACCESS read-only
	   STATUS mandatory
	   ::= { uxos-flckinfoEntry 4 }
					   
uxos-rectot OBJECT-TYPE
       SYNTAX Counter
	   ACCESS read-only
	   STATUS mandatory
	   ::= { uxos-flckinfoEntry 5 }


 --...................................................................
 -- Tune group
 --...................................................................

uxos-tuneTable OBJECT-TYPE
       SYNTAX SEQUENCE OF TuneEntry
	   ACCESS not-accessible
	   STATUS mandatory
	   ::= { uxos-tune 1 }

uxos-tuneEntry OBJECT-TYPE
       SYNTAX TuneEntry  
	   ACCESS not-accessible
	   STATUS mandatory
	   INDEX {uxos-tuneSysName,
		  uxos-tuneInstName,
		  uxos-tuneSubAddr}
	   ::= { uxos-tuneTable 1 }

TuneEntry ::= SEQUENCE {
                        uxos-tuneSysName 	DisplayString,
                       	uxos-tuneInstName 	DisplayString,
                       	uxos-tuneSubAddr 	DisplayString,
			uxos-tGpgslo		Counter,
			uxos-tGpgshi		Counter,
			uxos-tPadd		Counter,
			uxos-tNotused		Counter,
			uxos-tAgeinterval	Counter,
			uxos-tPadd11		Counter,
			uxos-tPadd12		Counter,
			uxos-tPadd13		Counter,
			uxos-tFsflushr		Counter,
			uxos-tMinarmem		Counter,
			uxos-tMinasmem		Counter,
			uxos-tDmalimit		Counter,
			uxos-tFlckrec		Counter,
			uxos-tMinakmem		Counter
						}
					   
					   
uxos-tuneSysName OBJECT-TYPE
       SYNTAX DisplayString (SIZE(0..14))
	   ACCESS read-only
	   STATUS mandatory
	   ::= { uxos-tuneEntry 1 }

uxos-tuneInstName OBJECT-TYPE
       SYNTAX DisplayString (SIZE(0..14))
	   ACCESS read-only
	   STATUS mandatory
	   ::= { uxos-tuneEntry 2 }

uxos-tuneSubAddr  OBJECT-TYPE
       SYNTAX DisplayString (SIZE(0..14))
	   ACCESS read-only
	   STATUS mandatory
	   ::= { uxos-tuneEntry 3 }

uxos-tGpgslo OBJECT-TYPE
       SYNTAX Counter
	   ACCESS read-only
	   STATUS mandatory
	   ::= { uxos-tuneEntry 4 }
					   
uxos-tGpgshi OBJECT-TYPE
       SYNTAX Counter
	   ACCESS read-only
	   STATUS mandatory
	   ::= { uxos-tuneEntry 5 }
					   
uxos-tPadd OBJECT-TYPE
       SYNTAX Counter
	   ACCESS read-only
	   STATUS mandatory
	   ::= { uxos-tuneEntry 6 }
					   
uxos-tNotused OBJECT-TYPE
       SYNTAX Counter
	   ACCESS not-accessible
	   STATUS mandatory
	   ::= { uxos-tuneEntry 7 }
					   
uxos-tAgeinterval OBJECT-TYPE
       SYNTAX Counter
	   ACCESS read-only
	   STATUS mandatory
	   ::= { uxos-tuneEntry 8 }
					   
uxos-tPadd11 OBJECT-TYPE
       SYNTAX Counter
	   ACCESS read-only
	   STATUS mandatory
	   ::= { uxos-tuneEntry 9 }
					   
uxos-tPadd12 OBJECT-TYPE
       SYNTAX Counter
	   ACCESS read-only
	   STATUS mandatory
	   ::= { uxos-tuneEntry 10 }
					   
uxos-tPadd13 OBJECT-TYPE
       SYNTAX Counter
	   ACCESS read-only
	   STATUS mandatory
	   ::= { uxos-tuneEntry 11 }
					   
uxos-tFsflushr OBJECT-TYPE
       SYNTAX Counter
	   ACCESS read-only
	   STATUS mandatory
	   ::= { uxos-tuneEntry 12 }
					   
uxos-tMinarmem OBJECT-TYPE
       SYNTAX Counter
	   ACCESS read-only
	   STATUS mandatory
	   ::= { uxos-tuneEntry 13 }
					   
uxos-tMinasmem OBJECT-TYPE
       SYNTAX Counter
	   ACCESS read-only
	   STATUS mandatory
	   ::= { uxos-tuneEntry 14 }
					   
uxos-tDmalimit OBJECT-TYPE
       SYNTAX Counter
	   ACCESS read-only
	   STATUS mandatory
	   ::= { uxos-tuneEntry 15 }
					   
uxos-tFlckrec OBJECT-TYPE
       SYNTAX Counter
	   ACCESS read-only
	   STATUS mandatory
	   ::= { uxos-tuneEntry 16 }
					   
uxos-tMinakmem OBJECT-TYPE
       SYNTAX Counter
	   ACCESS read-only
	   STATUS mandatory
	   ::= { uxos-tuneEntry 17 }


 --...................................................................
 -- Avenrun group
 --...................................................................

uxos-avenrunTable    OBJECT-TYPE
       SYNTAX SEQUENCE OF AvenrunEntry
	   ACCESS not-accessible
	   STATUS mandatory
	   ::= { uxos-avenrun 1 }

uxos-avenrunEntry    OBJECT-TYPE
       SYNTAX AvenrunEntry  
	   ACCESS not-accessible
	   STATUS mandatory
	   INDEX {uxos-avenrunSysName,
		  uxos-avenrunInstName,
		  uxos-avenrunSubAddr}
	   ::= { uxos-avenrunTable 1 }

AvenrunEntry ::= SEQUENCE {
                       uxos-avenrunSysName 	DisplayString,
                       uxos-avenrunInstName 	DisplayString,
                       uxos-avenrunSubAddr 	DisplayString,
                       uxos-avenrun1 		Counter,
                       uxos-avenrun2 		Counter,
                       uxos-avenrun3 		Counter
					   }
					   
uxos-avenrunSysName OBJECT-TYPE
       SYNTAX DisplayString (SIZE(0..14))
	   ACCESS read-only
	   STATUS mandatory
	   ::= { uxos-avenrunEntry 1 }

uxos-avenrunInstName OBJECT-TYPE
       SYNTAX DisplayString (SIZE(0..14))
	   ACCESS read-only
	   STATUS mandatory
	   ::= { uxos-avenrunEntry 2 }

uxos-avenrunSubAddr  OBJECT-TYPE
       SYNTAX DisplayString (SIZE(0..14))
	   ACCESS read-only
	   STATUS mandatory
	   ::= { uxos-avenrunEntry 3 }

uxos-avenrun1 OBJECT-TYPE
       SYNTAX Counter
	   ACCESS read-only
	   STATUS mandatory
	   ::= { uxos-avenrunEntry 4 }

uxos-avenrun2 OBJECT-TYPE
       SYNTAX Counter
	   ACCESS read-only
	   STATUS mandatory
	   ::= { uxos-avenrunEntry 5 }

uxos-avenrun3 OBJECT-TYPE
       SYNTAX Counter
	   ACCESS read-only
	   STATUS mandatory
	   ::= { uxos-avenrunEntry 6 }


 --...................................................................
 -- Vmcnt group
 --...................................................................

uxos-vmcntTable    OBJECT-TYPE
       SYNTAX SEQUENCE OF VmcntEntry
	   ACCESS not-accessible
	   STATUS mandatory
	   ::= { uxos-vmcnt 1 }

uxos-vmcntEntry    OBJECT-TYPE
       SYNTAX VmcntEntry  
	   ACCESS not-accessible
	   STATUS mandatory
	   INDEX {uxos-vmcntSysName,
		  uxos-vmcntInstName,
		  uxos-vmcntSubAddr}
	   ::= { uxos-vmcntTable 1 }

VmcntEntry ::= SEQUENCE {
                       uxos-vmcntSysName 	DisplayString,
                       uxos-vmcntInstName 	DisplayString,
                       uxos-vmcntSubAddr 	DisplayString,
                       uxos-cntvSwtch 		Counter,
                       uxos-cntvTrap 		Counter,
                       uxos-cntvSyscall 	Counter,
                       uxos-cntvIntr 		Counter,
                       uxos-cntvPdma 		Counter,
                       uxos-cntvPswpin 		Counter,
                       uxos-cntvPswpout 	Counter,
                       uxos-cntvPgin 		Counter,
                       uxos-cntvPgout 		Counter,
                       uxos-cntvPgpgin 		Counter,
                       uxos-cntvPgpgout 	Counter,
                       uxos-cntvIntrans 	Counter,
                       uxos-cntvPgrec 		Counter,
                       uxos-cntvXsfrec 		Counter,
                       uxos-cntvXifrec 		Counter,
                       uxos-cntvExfod 		Counter,
                       uxos-cntvZfod 		Counter,
                       uxos-cntvVrfod 		Counter,
                       uxos-cntvNexfod 		Counter,
                       uxos-cntvNzfod 		Counter,
                       uxos-cntvNvrfod 		Counter,
                       uxos-cntvPgfrec 		Counter,
                       uxos-cntvFaults 		Counter,
                       uxos-cntvScan 		Counter,
                       uxos-cntvRev 		Counter,
                       uxos-cntvSeqfree 	Counter,
                       uxos-cntvDfree 		Counter,
                       uxos-cntvFastpgrec 	Counter,
                       uxos-cntvSwpin 		Counter,
                       uxos-cntvSwpout 		Counter
					   }
					   

					   
uxos-vmcntSysName OBJECT-TYPE
       SYNTAX DisplayString (SIZE(0..14))
	   ACCESS read-only
	   STATUS mandatory
	   ::= { uxos-vmcntEntry 1 }

uxos-vmcntInstName OBJECT-TYPE
       SYNTAX DisplayString (SIZE(0..14))
	   ACCESS read-only
	   STATUS mandatory
	   ::= { uxos-vmcntEntry 2 }

uxos-vmcntSubAddr  OBJECT-TYPE
       SYNTAX DisplayString (SIZE(0..14))
	   ACCESS read-only
	   STATUS mandatory
	   ::= { uxos-vmcntEntry 3 }

uxos-cntvSwtch OBJECT-TYPE
       SYNTAX Counter
	   ACCESS read-only
	   STATUS mandatory
	   ::= { uxos-vmcntEntry 4 }

uxos-cntvTrap OBJECT-TYPE
       SYNTAX Counter
	   ACCESS read-only
	   STATUS mandatory
	   ::= { uxos-vmcntEntry 5 }

uxos-cntvSyscall OBJECT-TYPE
       SYNTAX Counter
	   ACCESS read-only
	   STATUS mandatory
	   ::= { uxos-vmcntEntry 6 }

uxos-cntvIntr OBJECT-TYPE
       SYNTAX Counter
	   ACCESS read-only
	   STATUS mandatory
	   ::= { uxos-vmcntEntry 7 }

uxos-cntvPdma OBJECT-TYPE
       SYNTAX Counter
	   ACCESS read-only
	   STATUS mandatory
	   ::= { uxos-vmcntEntry 8 }

uxos-cntvPswpin OBJECT-TYPE
       SYNTAX Counter
	   ACCESS read-only
	   STATUS mandatory
	   ::= { uxos-vmcntEntry 9 }

uxos-cntvPswpout OBJECT-TYPE
       SYNTAX Counter
	   ACCESS read-only
	   STATUS mandatory
	   ::= { uxos-vmcntEntry 10 }

uxos-cntvPgin OBJECT-TYPE
       SYNTAX Counter
	   ACCESS read-only
	   STATUS mandatory
	   ::= { uxos-vmcntEntry 11 }

uxos-cntvPgout OBJECT-TYPE
       SYNTAX Counter
	   ACCESS read-only
	   STATUS mandatory
	   ::= { uxos-vmcntEntry 12 }

uxos-cntvPgpgin OBJECT-TYPE
       SYNTAX Counter
	   ACCESS read-only
	   STATUS mandatory
	   ::= { uxos-vmcntEntry 13 }

uxos-cntvPgpgout OBJECT-TYPE
       SYNTAX Counter
	   ACCESS read-only
	   STATUS mandatory
	   ::= { uxos-vmcntEntry 14 }

uxos-cntvIntrans OBJECT-TYPE
       SYNTAX Counter
	   ACCESS read-only
	   STATUS mandatory
	   ::= { uxos-vmcntEntry 15 }

uxos-cntvPgrec OBJECT-TYPE
       SYNTAX Counter
	   ACCESS read-only
	   STATUS mandatory
	   ::= { uxos-vmcntEntry 16 }

uxos-cntvXsfrec OBJECT-TYPE
       SYNTAX Counter
	   ACCESS read-only
	   STATUS mandatory
	   ::= { uxos-vmcntEntry 17 }

uxos-cntvXifrec OBJECT-TYPE
       SYNTAX Counter
	   ACCESS read-only
	   STATUS mandatory
	   ::= { uxos-vmcntEntry 18 }

uxos-cntvExfod OBJECT-TYPE
       SYNTAX Counter
	   ACCESS not-accessible
	   STATUS mandatory
	   ::= { uxos-vmcntEntry 19 }

uxos-cntvZfod OBJECT-TYPE
       SYNTAX Counter
	   ACCESS read-only
	   STATUS mandatory
	   ::= { uxos-vmcntEntry 20 }

uxos-cntvVrfod OBJECT-TYPE
       SYNTAX Counter
	   ACCESS not-accessible
	   STATUS mandatory
	   ::= { uxos-vmcntEntry 21 }

uxos-cntvNexfod OBJECT-TYPE
       SYNTAX Counter
	   ACCESS not-accessible
	   STATUS mandatory
	   ::= { uxos-vmcntEntry 22 }

uxos-cntvNzfod OBJECT-TYPE
       SYNTAX Counter
	   ACCESS not-accessible
	   STATUS mandatory
	   ::= { uxos-vmcntEntry 23 }

uxos-cntvNvrfod OBJECT-TYPE
       SYNTAX Counter
	   ACCESS not-accessible
	   STATUS mandatory
	   ::= { uxos-vmcntEntry 24 }

uxos-cntvPgfrec OBJECT-TYPE
       SYNTAX Counter
	   ACCESS read-only
	   STATUS mandatory
	   ::= { uxos-vmcntEntry 25 }

uxos-cntvFaults OBJECT-TYPE
       SYNTAX Counter
	   ACCESS read-only
	   STATUS mandatory
	   ::= { uxos-vmcntEntry 26 }

uxos-cntvScan OBJECT-TYPE
       SYNTAX Counter
	   ACCESS read-only
	   STATUS mandatory
	   ::= { uxos-vmcntEntry 27 }

uxos-cntvRev OBJECT-TYPE
       SYNTAX Counter
	   ACCESS read-only
	   STATUS mandatory
	   ::= { uxos-vmcntEntry 28 }

uxos-cntvSeqfree OBJECT-TYPE
       SYNTAX Counter
	   ACCESS not-accessible
	   STATUS mandatory
	   ::= { uxos-vmcntEntry 29 }

uxos-cntvDfree OBJECT-TYPE
       SYNTAX Counter
	   ACCESS read-only
	   STATUS mandatory
	   ::= { uxos-vmcntEntry 30 }

uxos-cntvFastpgrec OBJECT-TYPE
       SYNTAX Counter
	   ACCESS not-accessible
	   STATUS mandatory
	   ::= { uxos-vmcntEntry 31 }

uxos-cntvSwpin OBJECT-TYPE
       SYNTAX Counter
	   ACCESS read-only
	   STATUS mandatory
	   ::= { uxos-vmcntEntry 32 }

uxos-cntvSwpout OBJECT-TYPE
       SYNTAX Counter
	   ACCESS read-only
	   STATUS mandatory
	   ::= { uxos-vmcntEntry 33 }


 --...................................................................
 -- Vmrate group
 --...................................................................

uxos-vmrateTable    OBJECT-TYPE
       SYNTAX SEQUENCE OF VmrateEntry
	   ACCESS not-accessible
	   STATUS mandatory
	   ::= { uxos-vmrate 1 }

uxos-vmrateEntry    OBJECT-TYPE
       SYNTAX VmrateEntry  
	   ACCESS not-accessible
	   STATUS mandatory
	   INDEX {uxos-vmrateSysName,
		  uxos-vmrateInstName,
		  uxos-vmrateSubAddr}
	   ::= { uxos-vmrateTable 1 }

VmrateEntry ::= SEQUENCE {
                       uxos-vmrateSysName 	DisplayString,
                       uxos-vmrateInstName 	DisplayString,
                       uxos-vmrateSubAddr 	DisplayString,
                       uxos-ratevSwtch 		Counter,
                       uxos-ratevTrap		Counter,
                       uxos-ratevSyscall 	Counter,
                       uxos-ratevIntr 		Counter,
                       uxos-ratevPdma 		Counter,
                       uxos-ratevPswpin 	Counter,
                       uxos-ratevPswpout 	Counter,
                       uxos-ratevPgin 		Counter,
                       uxos-ratevPgout 		Counter,
                       uxos-ratevPgpgin 	Counter,
                       uxos-ratevPgpgout 	Counter,
                       uxos-ratevIntrans 	Counter,
                       uxos-ratevPgrec 		Counter,
                       uxos-ratevXsfrec 	Counter,
                       uxos-ratevXifrec 	Counter,
                       uxos-ratevExfod 		Counter,
                       uxos-ratevZfod 		Counter,
                       uxos-ratevVrfod 		Counter,
                       uxos-ratevNexfod 	Counter,
                       uxos-ratevNzfod 		Counter,
                       uxos-ratevNvrfod 	Counter,
                       uxos-ratevPgfrec 	Counter,
                       uxos-ratevFaults 	Counter,
                       uxos-ratevScan 		Counter,
                       uxos-ratevRev 		Counter,
                       uxos-ratevSeqfree 	Counter,
                       uxos-ratevDfree 		Counter,
                       uxos-ratevFastpgrec 	Counter,
                       uxos-ratevSwpin 		Counter,
                       uxos-ratevSwpout 	Counter
					   }
					   

					   
uxos-vmrateSysName OBJECT-TYPE
       SYNTAX DisplayString (SIZE(0..14))
	   ACCESS read-only
	   STATUS mandatory
	   ::= { uxos-vmrateEntry 1 }

uxos-vmrateInstName OBJECT-TYPE
       SYNTAX DisplayString (SIZE(0..14))
	   ACCESS read-only
	   STATUS mandatory
	   ::= { uxos-vmrateEntry 2 }

uxos-vmrateSubAddr  OBJECT-TYPE
       SYNTAX DisplayString (SIZE(0..14))
	   ACCESS read-only
	   STATUS mandatory
	   ::= { uxos-vmrateEntry 3 }

uxos-ratevSwtch OBJECT-TYPE
       SYNTAX Counter
	   ACCESS read-only
	   STATUS mandatory
	   ::= { uxos-vmrateEntry 4 }

uxos-ratevTrap OBJECT-TYPE
       SYNTAX Counter
	   ACCESS read-only
	   STATUS mandatory
	   ::= { uxos-vmrateEntry 5 }

uxos-ratevSyscall OBJECT-TYPE
       SYNTAX Counter
	   ACCESS read-only
	   STATUS mandatory
	   ::= { uxos-vmrateEntry 6 }

uxos-ratevIntr OBJECT-TYPE
       SYNTAX Counter
	   ACCESS read-only
	   STATUS mandatory
	   ::= { uxos-vmrateEntry 7 }

uxos-ratevPdma OBJECT-TYPE
       SYNTAX Counter
	   ACCESS read-only
	   STATUS mandatory
	   ::= { uxos-vmrateEntry 8 }

uxos-ratevPswpin OBJECT-TYPE
       SYNTAX Counter
	   ACCESS read-only
	   STATUS mandatory
	   ::= { uxos-vmrateEntry 9 }

uxos-ratevPswpout OBJECT-TYPE
       SYNTAX Counter
	   ACCESS read-only
	   STATUS mandatory
	   ::= { uxos-vmrateEntry 10 }

uxos-ratevPgin OBJECT-TYPE
       SYNTAX Counter
	   ACCESS read-only
	   STATUS mandatory
	   ::= { uxos-vmrateEntry 11 }

uxos-ratevPgout OBJECT-TYPE
       SYNTAX Counter
	   ACCESS read-only
	   STATUS mandatory
	   ::= { uxos-vmrateEntry 12 }

uxos-ratevPgpgin OBJECT-TYPE
       SYNTAX Counter
	   ACCESS read-only
	   STATUS mandatory
	   ::= { uxos-vmrateEntry 13 }

uxos-ratevPgpgout OBJECT-TYPE
       SYNTAX Counter
	   ACCESS read-only
	   STATUS mandatory
	   ::= { uxos-vmrateEntry 14 }

uxos-ratevIntrans OBJECT-TYPE
       SYNTAX Counter
	   ACCESS read-only
	   STATUS mandatory
	   ::= { uxos-vmrateEntry 15 }

uxos-ratevPgrec OBJECT-TYPE
       SYNTAX Counter
	   ACCESS read-only
	   STATUS mandatory
	   ::= { uxos-vmrateEntry 16 }

uxos-ratevXsfrec OBJECT-TYPE
       SYNTAX Counter
	   ACCESS read-only
	   STATUS mandatory
	   ::= { uxos-vmrateEntry 17 }

uxos-ratevXifrec OBJECT-TYPE
       SYNTAX Counter
	   ACCESS read-only
	   STATUS mandatory
	   ::= { uxos-vmrateEntry 18 }

uxos-ratevExfod OBJECT-TYPE
       SYNTAX Counter
	   ACCESS not-accessible
	   STATUS mandatory
	   ::= { uxos-vmrateEntry 19 }

uxos-ratevZfod OBJECT-TYPE
       SYNTAX Counter
	   ACCESS read-only
	   STATUS mandatory
	   ::= { uxos-vmrateEntry 20 }

uxos-ratevVrfod OBJECT-TYPE
       SYNTAX Counter
	   ACCESS not-accessible
	   STATUS mandatory
	   ::= { uxos-vmrateEntry 21 }

uxos-ratevNexfod OBJECT-TYPE
       SYNTAX Counter
	   ACCESS not-accessible
	   STATUS mandatory
	   ::= { uxos-vmrateEntry 22 }

uxos-ratevNzfod OBJECT-TYPE
       SYNTAX Counter
	   ACCESS not-accessible
	   STATUS mandatory
	   ::= { uxos-vmrateEntry 23 }

uxos-ratevNvrfod OBJECT-TYPE
       SYNTAX Counter
	   ACCESS not-accessible
	   STATUS mandatory
	   ::= { uxos-vmrateEntry 24 }

uxos-ratevPgfrec OBJECT-TYPE
       SYNTAX Counter
	   ACCESS read-only
	   STATUS mandatory
	   ::= { uxos-vmrateEntry 25 }

uxos-ratevFaults OBJECT-TYPE
       SYNTAX Counter
	   ACCESS read-only
	   STATUS mandatory
	   ::= { uxos-vmrateEntry 26 }

uxos-ratevScan OBJECT-TYPE
       SYNTAX Counter
	   ACCESS read-only
	   STATUS mandatory
	   ::= { uxos-vmrateEntry 27 }

uxos-ratevRev OBJECT-TYPE
       SYNTAX Counter
	   ACCESS read-only
	   STATUS mandatory
	   ::= { uxos-vmrateEntry 28 }

uxos-ratevSeqfree OBJECT-TYPE
       SYNTAX Counter
	   ACCESS not-accessible
	   STATUS mandatory
	   ::= { uxos-vmrateEntry 29 }

uxos-ratevDfree OBJECT-TYPE
       SYNTAX Counter
	   ACCESS read-only
	   STATUS mandatory
	   ::= { uxos-vmrateEntry 30 }

uxos-ratevFastpgrec OBJECT-TYPE
       SYNTAX Counter
	   ACCESS not-accessible
	   STATUS mandatory
	   ::= { uxos-vmrateEntry 31 }

uxos-ratevSwpin OBJECT-TYPE
       SYNTAX Counter
	   ACCESS read-only
	   STATUS mandatory
	   ::= { uxos-vmrateEntry 32 }

uxos-ratevSwpout OBJECT-TYPE
       SYNTAX Counter
	   ACCESS read-only
	   STATUS mandatory
	   ::= { uxos-vmrateEntry 33 }


 --...................................................................
 -- Vmsum group
 --...................................................................

uxos-vmsumTable    OBJECT-TYPE
       SYNTAX SEQUENCE OF VmsumEntry
	   ACCESS not-accessible
	   STATUS mandatory
	   ::= { uxos-vmsum 1 }

uxos-vmsumEntry    OBJECT-TYPE
       SYNTAX VmsumEntry  
	   ACCESS not-accessible
	   STATUS mandatory
	   INDEX {uxos-vmsumSysName,
		  uxos-vmsumInstName,
		  uxos-vmsumSubAddr}
	   ::= { uxos-vmsumTable 1 }

VmsumEntry ::= SEQUENCE {
                       uxos-vmsumSysName 	DisplayString,
                       uxos-vmsumInstName 	DisplayString,
                       uxos-vmsumSubAddr 	DisplayString,
                       uxos-sumvSwtch 		Counter,
                       uxos-sumvTrap 		Counter,
                       uxos-sumvSyscall 	Counter,
                       uxos-sumvIntr 		Counter,
                       uxos-sumvPdma 		Counter,
                       uxos-sumvPswpin 		Counter,
                       uxos-sumvPswpout 	Counter,
                       uxos-sumvPgin 		Counter,
                       uxos-sumvPgout 		Counter,
                       uxos-sumvPgpgin 		Counter,
                       uxos-sumvPgpgout 	Counter,
                       uxos-sumvIntrans 	Counter,
                       uxos-sumvPgrec 		Counter,
                       uxos-sumvXsfrec 		Counter,
                       uxos-sumvXifrec 		Counter,
                       uxos-sumvExfod 		Counter,
                       uxos-sumvZfod 		Counter,
                       uxos-sumvVrfod 		Counter,
                       uxos-sumvNexfod 		Counter,
                       uxos-sumvNzfod 		Counter,
                       uxos-sumvNvrfod 		Counter,
                       uxos-sumvPgfrec 		Counter,
                       uxos-sumvFaults 		Counter,
                       uxos-sumvScan 		Counter,
                       uxos-sumvRev 		Counter,
                       uxos-sumvSeqfree 	Counter,
                       uxos-sumvDfree 		Counter,
                       uxos-sumvFastpgrec 	Counter,
                       uxos-sumvSwpin 		Counter,
                       uxos-sumvSwpout 		Counter
					   }
					   

					   
uxos-vmsumSysName OBJECT-TYPE
       SYNTAX DisplayString (SIZE(0..14))
	   ACCESS read-only
	   STATUS mandatory
	   ::= { uxos-vmsumEntry 1 }

uxos-vmsumInstName OBJECT-TYPE
       SYNTAX DisplayString (SIZE(0..14))
	   ACCESS read-only
	   STATUS mandatory
	   ::= { uxos-vmsumEntry 2 }

uxos-vmsumSubAddr  OBJECT-TYPE
       SYNTAX DisplayString (SIZE(0..14))
	   ACCESS read-only
	   STATUS mandatory
	   ::= { uxos-vmsumEntry 3 }

uxos-sumvSwtch OBJECT-TYPE
       SYNTAX Counter
	   ACCESS read-only
	   STATUS mandatory
	   ::= { uxos-vmsumEntry 4 }

uxos-sumvTrap OBJECT-TYPE
       SYNTAX Counter
	   ACCESS read-only
	   STATUS mandatory
	   ::= { uxos-vmsumEntry 5 }

uxos-sumvSyscall OBJECT-TYPE
       SYNTAX Counter
	   ACCESS read-only
	   STATUS mandatory
	   ::= { uxos-vmsumEntry 6 }

uxos-sumvIntr OBJECT-TYPE
       SYNTAX Counter
	   ACCESS read-only
	   STATUS mandatory
	   ::= { uxos-vmsumEntry 7 }

uxos-sumvPdma OBJECT-TYPE
       SYNTAX Counter
	   ACCESS read-only
	   STATUS mandatory
	   ::= { uxos-vmsumEntry 8 }

uxos-sumvPswpin OBJECT-TYPE
       SYNTAX Counter
	   ACCESS read-only
	   STATUS mandatory
	   ::= { uxos-vmsumEntry 9 }

uxos-sumvPswpout OBJECT-TYPE
       SYNTAX Counter
	   ACCESS read-only
	   STATUS mandatory
	   ::= { uxos-vmsumEntry 10 }

uxos-sumvPgin OBJECT-TYPE
       SYNTAX Counter
	   ACCESS read-only
	   STATUS mandatory
	   ::= { uxos-vmsumEntry 11 }

uxos-sumvPgout OBJECT-TYPE
       SYNTAX Counter
	   ACCESS read-only
	   STATUS mandatory
	   ::= { uxos-vmsumEntry 12 }

uxos-sumvPgpgin OBJECT-TYPE
       SYNTAX Counter
	   ACCESS read-only
	   STATUS mandatory
	   ::= { uxos-vmsumEntry 13 }

uxos-sumvPgpgout OBJECT-TYPE
       SYNTAX Counter
	   ACCESS read-only
	   STATUS mandatory
	   ::= { uxos-vmsumEntry 14 }

uxos-sumvIntrans OBJECT-TYPE
       SYNTAX Counter
	   ACCESS read-only
	   STATUS mandatory
	   ::= { uxos-vmsumEntry 15 }

uxos-sumvPgrec OBJECT-TYPE
       SYNTAX Counter
	   ACCESS read-only
	   STATUS mandatory
	   ::= { uxos-vmsumEntry 16 }

uxos-sumvXsfrec OBJECT-TYPE
       SYNTAX Counter
	   ACCESS read-only
	   STATUS mandatory
	   ::= { uxos-vmsumEntry 17 }

uxos-sumvXifrec OBJECT-TYPE
       SYNTAX Counter
	   ACCESS read-only
	   STATUS mandatory
	   ::= { uxos-vmsumEntry 18 }

uxos-sumvExfod OBJECT-TYPE
       SYNTAX Counter
	   ACCESS not-accessible
	   STATUS mandatory
	   ::= { uxos-vmsumEntry 19 }

uxos-sumvZfod OBJECT-TYPE
       SYNTAX Counter
	   ACCESS read-only
	   STATUS mandatory
	   ::= { uxos-vmsumEntry 20 }

uxos-sumvVrfod OBJECT-TYPE
       SYNTAX Counter
	   ACCESS not-accessible
	   STATUS mandatory
	   ::= { uxos-vmsumEntry 21 }

uxos-sumvNexfod OBJECT-TYPE
       SYNTAX Counter
	   ACCESS not-accessible
	   STATUS mandatory
	   ::= { uxos-vmsumEntry 22 }

uxos-sumvNzfod OBJECT-TYPE
       SYNTAX Counter
	   ACCESS not-accessible
	   STATUS mandatory
	   ::= { uxos-vmsumEntry 23 }

uxos-sumvNvrfod OBJECT-TYPE
       SYNTAX Counter
	   ACCESS not-accessible
	   STATUS mandatory
	   ::= { uxos-vmsumEntry 24 }

uxos-sumvPgfrec OBJECT-TYPE
       SYNTAX Counter
	   ACCESS read-only
	   STATUS mandatory
	   ::= { uxos-vmsumEntry 25 }

uxos-sumvFaults OBJECT-TYPE
       SYNTAX Counter
	   ACCESS read-only
	   STATUS mandatory
	   ::= { uxos-vmsumEntry 26 }

uxos-sumvScan OBJECT-TYPE
       SYNTAX Counter
	   ACCESS read-only
	   STATUS mandatory
	   ::= { uxos-vmsumEntry 27 }

uxos-sumvRev OBJECT-TYPE
       SYNTAX Counter
	   ACCESS read-only
	   STATUS mandatory
	   ::= { uxos-vmsumEntry 28 }

uxos-sumvSeqfree OBJECT-TYPE
       SYNTAX Counter
	   ACCESS not-accessible
	   STATUS mandatory
	   ::= { uxos-vmsumEntry 29 }

uxos-sumvDfree OBJECT-TYPE
       SYNTAX Counter
	   ACCESS read-only
	   STATUS mandatory
	   ::= { uxos-vmsumEntry 30 }

uxos-sumvFastpgrec OBJECT-TYPE
       SYNTAX Counter
	   ACCESS not-accessible
	   STATUS mandatory
	   ::= { uxos-vmsumEntry 31 }

uxos-sumvSwpin OBJECT-TYPE
       SYNTAX Counter
	   ACCESS read-only
	   STATUS mandatory
	   ::= { uxos-vmsumEntry 32 }

uxos-sumvSwpout OBJECT-TYPE
       SYNTAX Counter
	   ACCESS read-only
	   STATUS mandatory
	   ::= { uxos-vmsumEntry 33 }


 --...................................................................
 -- Vmtotal group
 --...................................................................

uxos-vmtotalTable    OBJECT-TYPE
       SYNTAX SEQUENCE OF VmtotalEntry
	   ACCESS not-accessible
	   STATUS mandatory
	   ::= { uxos-vmtotal 1 }

uxos-vmtotalEntry    OBJECT-TYPE
       SYNTAX VmtotalEntry  
	   ACCESS not-accessible
	   STATUS mandatory
	   INDEX {uxos-vmtotalSysName,
		  uxos-vmtotalInstName,
		  uxos-vmtotalSubAddr}
	   ::= { uxos-vmtotalTable 1 }

VmtotalEntry ::= SEQUENCE {
                       uxos-vmtotalSysName 	DisplayString,
                       uxos-vmtotalInstName 	DisplayString,
                       uxos-vmtotalSubAddr 	DisplayString,
                       uxos-tRq 	Counter,
                       uxos-tDw 	Counter,
                       uxos-tPw 	Counter,
                       uxos-tSl 	Counter,
                       uxos-tSw 	Counter,
                       uxos-tVm 	Counter,
                       uxos-tAvm 	Counter,
                       uxos-tRm 	Counter,
                       uxos-tArm 	Counter,
                       uxos-tVmtxt 	Counter,
                       uxos-tAvmtxt 	Counter,
                       uxos-tRmtxt 	Counter,
                       uxos-tArmtxt 	Counter,
                       uxos-tFree 	Counter
						}

					   
uxos-vmtotalSysName OBJECT-TYPE
       SYNTAX DisplayString (SIZE(0..14))
	   ACCESS read-only
	   STATUS mandatory
	   ::= { uxos-vmtotalEntry 1 }

uxos-vmtotalInstName OBJECT-TYPE
       SYNTAX DisplayString (SIZE(0..14))
	   ACCESS read-only
	   STATUS mandatory
	   ::= { uxos-vmtotalEntry 2 }

uxos-vmtotalSubAddr  OBJECT-TYPE
       SYNTAX DisplayString (SIZE(0..14))
	   ACCESS read-only
	   STATUS mandatory
	   ::= { uxos-vmtotalEntry 3 }

uxos-tRq OBJECT-TYPE
       SYNTAX Counter
	   ACCESS read-only
	   STATUS mandatory
	   ::= { uxos-vmtotalEntry 4 }

uxos-tDw OBJECT-TYPE
       SYNTAX Counter
	   ACCESS read-only
	   STATUS mandatory
	   ::= { uxos-vmtotalEntry 5 }

uxos-tPw OBJECT-TYPE
       SYNTAX Counter
	   ACCESS read-only
	   STATUS mandatory
	   ::= { uxos-vmtotalEntry 6 }

uxos-tSl OBJECT-TYPE
       SYNTAX Counter
	   ACCESS read-only
	   STATUS mandatory
	   ::= { uxos-vmtotalEntry 7 }

uxos-tSw OBJECT-TYPE
       SYNTAX Counter
	   ACCESS read-only
	   STATUS mandatory
	   ::= { uxos-vmtotalEntry 8 }

uxos-tVm OBJECT-TYPE
       SYNTAX Counter
	   ACCESS not-accessible
	   STATUS mandatory
	   ::= { uxos-vmtotalEntry 9 }

uxos-tAvm OBJECT-TYPE
       SYNTAX Counter
	   ACCESS not-accessible
	   STATUS mandatory
	   ::= { uxos-vmtotalEntry 10 }

uxos-tRm OBJECT-TYPE
       SYNTAX Counter
	   ACCESS read-only
	   STATUS mandatory
	   ::= { uxos-vmtotalEntry 11 }

uxos-tArm OBJECT-TYPE
       SYNTAX Counter
	   ACCESS read-only
	   STATUS mandatory
	   ::= { uxos-vmtotalEntry 12 }

uxos-tVmtxt OBJECT-TYPE
       SYNTAX Counter
	   ACCESS read-only
	   STATUS mandatory
	   ::= { uxos-vmtotalEntry 13 }

uxos-tAvmtxt OBJECT-TYPE
       SYNTAX Counter
	   ACCESS not-accessible
	   STATUS mandatory
	   ::= { uxos-vmtotalEntry 14 }

uxos-tRmtxt OBJECT-TYPE
       SYNTAX Counter
	   ACCESS not-accessible
	   STATUS mandatory
	   ::= { uxos-vmtotalEntry 15 }

uxos-tArmtxt OBJECT-TYPE
       SYNTAX Counter
	   ACCESS not-accessible
	   STATUS mandatory
	   ::= { uxos-vmtotalEntry 16 }

uxos-tFree OBJECT-TYPE
       SYNTAX Counter
	   ACCESS read-only
	   STATUS mandatory
	   ::= { uxos-vmtotalEntry 17 }

--..........................................................................
-- Namecache group
--..........................................................................

uxos-namecacheTable    OBJECT-TYPE
       SYNTAX SEQUENCE OF NamecacheEntry
	   ACCESS not-accessible
	   STATUS mandatory
	   ::= { uxos-namecache 1 }

uxos-namecacheEntry    OBJECT-TYPE
       SYNTAX NamecacheEntry  
	   ACCESS not-accessible
	   STATUS mandatory
	   INDEX {uxos-namecacheSysName,
		  uxos-namecacheInstName,
		  uxos-namecacheSubAddr}
	   ::= { uxos-namecacheTable 1 }

NamecacheEntry ::= SEQUENCE {
                       uxos-namecacheSysName 	DisplayString,
                       uxos-namecacheInstName 	DisplayString,
                       uxos-namecacheSubAddr 	DisplayString,
                       uxos-hits 	Counter,
                       uxos-misses 	Counter,
                       uxos-enters 	Counter,
                       uxos-dblEnters 	Counter,
                       uxos-longEnter 	Counter,
                       uxos-longLook 	Counter,
                       uxos-lruEmpty 	Counter,
                       uxos-purges 	Counter
					}

					   
uxos-namecacheSysName OBJECT-TYPE
       SYNTAX DisplayString (SIZE(0..14))
	   ACCESS read-only
	   STATUS mandatory
	   ::= { uxos-namecacheEntry 1 }

uxos-namecacheInstName OBJECT-TYPE
       SYNTAX DisplayString (SIZE(0..14))
	   ACCESS read-only
	   STATUS mandatory
	   ::= { uxos-namecacheEntry 2 }

uxos-namecacheSubAddr  OBJECT-TYPE
       SYNTAX DisplayString (SIZE(0..14))
	   ACCESS read-only
	   STATUS mandatory
	   ::= { uxos-namecacheEntry 3 }

uxos-hits OBJECT-TYPE
       SYNTAX Counter
	   ACCESS read-only
	   STATUS mandatory
	   ::= { uxos-namecacheEntry 4 }

uxos-misses OBJECT-TYPE
       SYNTAX Counter
	   ACCESS read-only
	   STATUS mandatory
	   ::= { uxos-namecacheEntry 5 }

uxos-enters OBJECT-TYPE
       SYNTAX Counter
	   ACCESS read-only
	   STATUS mandatory
	   ::= { uxos-namecacheEntry 6 }

uxos-dblEnters OBJECT-TYPE
       SYNTAX Counter
	   ACCESS read-only
	   STATUS mandatory
	   ::= { uxos-namecacheEntry 7 }

uxos-longEnter OBJECT-TYPE
       SYNTAX Counter
	   ACCESS read-only
	   STATUS mandatory
	   ::= { uxos-namecacheEntry 8 }

uxos-longLook OBJECT-TYPE
       SYNTAX Counter
	   ACCESS read-only
	   STATUS mandatory
	   ::= { uxos-namecacheEntry 9 }

uxos-lruEmpty OBJECT-TYPE
       SYNTAX Counter
	   ACCESS not-accessible
	   STATUS mandatory
	   ::= { uxos-namecacheEntry 10 }

uxos-purges OBJECT-TYPE
       SYNTAX Counter
	   ACCESS read-only
	   STATUS mandatory
	   ::= { uxos-namecacheEntry 11 }

--............................................................................
-- Buffercache group
--............................................................................

uxos-buffercacheTable    OBJECT-TYPE
       SYNTAX SEQUENCE OF BuffercacheEntry
	   ACCESS not-accessible
	   STATUS mandatory
	   ::= { uxos-buffercache 1 }

uxos-buffercacheEntry    OBJECT-TYPE
       SYNTAX BuffercacheEntry  
	   ACCESS not-accessible
	   STATUS mandatory
	   INDEX {uxos-buffercacheSysName,
		  uxos-buffercacheInstName,
		  uxos-buffercacheSubAddr}
	   ::= { uxos-buffercacheTable 1 }

BuffercacheEntry ::= SEQUENCE {
                       uxos-buffercacheSysName 	DisplayString,
                       uxos-buffercacheInstName DisplayString,
                       uxos-buffercacheSubAddr DisplayString,
                       uxos-cachehit 		Counter,
                       uxos-cachemiss 		Counter,
                       uxos-freehit 		Counter,
                       uxos-freemiss 		Counter,
                       uxos-bbusy 		Counter,
                       uxos-pfreemiss 		Counter,
                       uxos-prepfreemiss 	Counter,
                       uxos-spare 		Counter
					}

					   
uxos-buffercacheSysName OBJECT-TYPE
       SYNTAX DisplayString (SIZE(0..14))
	   ACCESS read-only
	   STATUS mandatory
	   ::= { uxos-buffercacheEntry 1 }

uxos-buffercacheInstName OBJECT-TYPE
       SYNTAX DisplayString (SIZE(0..14))
	   ACCESS read-only
	   STATUS mandatory
	   ::= { uxos-buffercacheEntry 2 }

uxos-buffercacheSubAddr  OBJECT-TYPE
       SYNTAX DisplayString (SIZE(0..14))
	   ACCESS read-only
	   STATUS mandatory
	   ::= { uxos-buffercacheEntry 3 }

uxos-cachehit OBJECT-TYPE
       SYNTAX Counter
	   ACCESS read-only
	   STATUS mandatory
	   ::= { uxos-buffercacheEntry 4 }

uxos-cachemiss OBJECT-TYPE
       SYNTAX Counter
	   ACCESS read-only
	   STATUS mandatory
	   ::= { uxos-buffercacheEntry 5 }

uxos-freehit OBJECT-TYPE
       SYNTAX Counter
	   ACCESS read-only
	   STATUS mandatory
	   ::= { uxos-buffercacheEntry 6 }

uxos-freemiss OBJECT-TYPE
       SYNTAX Counter
	   ACCESS read-only
	   STATUS mandatory
	   ::= { uxos-buffercacheEntry 7 }

uxos-bbusy OBJECT-TYPE
       SYNTAX Counter
	   ACCESS read-only
	   STATUS mandatory
	   ::= { uxos-buffercacheEntry 8 }

uxos-pfreemiss OBJECT-TYPE
       SYNTAX Counter
	   ACCESS read-only
	   STATUS mandatory
	   ::= { uxos-buffercacheEntry 9 }

uxos-prepfreemiss OBJECT-TYPE
       SYNTAX Counter
	   ACCESS read-only
	   STATUS mandatory
	   ::= { uxos-buffercacheEntry 10 }

uxos-spare OBJECT-TYPE
       SYNTAX Counter
	   ACCESS not-accessible
	   STATUS mandatory
	   ::= { uxos-buffercacheEntry 11 }


--...................................................................
-- Aioinfo group
--...................................................................

uxos-aioTable OBJECT-TYPE
       SYNTAX SEQUENCE OF AioEntry
	   ACCESS not-accessible
	   STATUS mandatory
	   ::= { uxos-aioinfo 1 }

uxos-aioEntry OBJECT-TYPE
       SYNTAX AioEntry  
	   ACCESS not-accessible
	   STATUS mandatory
	   INDEX {uxos-aioSysName,
		  uxos-aioInstName,
		  uxos-aioSubAddr}
	   ::= { uxos-aioTable 1 }

AioEntry ::= SEQUENCE {
                       uxos-aioSysName 	DisplayString,
                       uxos-aioInstName DisplayString,
                       uxos-aioSubAddr	DisplayString,
                       uxos-aioread   	Counter,
                       uxos-aiowrite   	Counter,
                       uxos-aiolock   	Counter,
                       uxos-aiopoll   	Counter,
                       uxos-aiohfbuf   	Counter,
                       uxos-aiohab   	Counter,
                       uxos-aiomsb   	Counter
						}
					   
					   
uxos-aioSysName OBJECT-TYPE
       SYNTAX DisplayString (SIZE(0..14))
	   ACCESS read-only
	   STATUS mandatory
	   ::= { uxos-aioEntry 1 }

uxos-aioInstName OBJECT-TYPE
       SYNTAX DisplayString (SIZE(0..14))
	   ACCESS read-only
	   STATUS mandatory
	   ::= { uxos-aioEntry 2 }

uxos-aioSubAddr  OBJECT-TYPE
       SYNTAX DisplayString (SIZE(0..14))
	   ACCESS read-only
	   STATUS mandatory
	   ::= { uxos-aioEntry 3 }

uxos-aioread OBJECT-TYPE
       SYNTAX Counter
	   ACCESS read-only
	   STATUS mandatory
	   ::= { uxos-aioEntry 4 }

uxos-aiowrite OBJECT-TYPE
       SYNTAX Counter
	   ACCESS read-only
	   STATUS mandatory
	   ::= { uxos-aioEntry 5 }

uxos-aiolock OBJECT-TYPE
       SYNTAX Counter
	   ACCESS read-only
	   STATUS mandatory
	   ::= { uxos-aioEntry 6 }

uxos-aiopoll OBJECT-TYPE
       SYNTAX Counter
	   ACCESS read-only
	   STATUS mandatory
	   ::= { uxos-aioEntry 7}

uxos-aiohfbuf OBJECT-TYPE
       SYNTAX Counter
	   ACCESS read-only
	   STATUS mandatory
	   ::= { uxos-aioEntry 8 }

uxos-aiohab OBJECT-TYPE
       SYNTAX Counter
	   ACCESS read-only
	   STATUS mandatory
	   ::= { uxos-aioEntry 9 }

uxos-aiomsb OBJECT-TYPE
       SYNTAX Counter
	   ACCESS read-only
	   STATUS mandatory
	   ::= { uxos-aioEntry 10 }
					   

--...................................................................
-- Lioinfo group
--...................................................................

uxos-lioTable OBJECT-TYPE
       SYNTAX SEQUENCE OF LioEntry
	   ACCESS not-accessible
	   STATUS mandatory
	   ::= { uxos-lioinfo 1 }

uxos-lioEntry OBJECT-TYPE
       SYNTAX LioEntry  
	   ACCESS not-accessible
	   STATUS mandatory
	   INDEX {uxos-lioSysName,
		  uxos-lioInstName,
		  uxos-lioSubAddr}
	   ::= { uxos-lioTable 1 }

LioEntry ::= SEQUENCE {
                       uxos-lioSysName 	DisplayString,
                       uxos-lioInstName DisplayString,
                       uxos-lioSubAddr	DisplayString,
                       uxos-liocall   	Counter,
                       uxos-lioread   	Counter,
                       uxos-liowrite   	Counter,
                       uxos-liolock   	Counter,
                       uxos-liopoll   	Counter,
                       uxos-liowait   	Counter
						}
					   
					   
uxos-lioSysName OBJECT-TYPE
       SYNTAX DisplayString (SIZE(0..14))
	   ACCESS read-only
	   STATUS mandatory
	   ::= { uxos-lioEntry 1 }

uxos-lioInstName OBJECT-TYPE
       SYNTAX DisplayString (SIZE(0..14))
	   ACCESS read-only
	   STATUS mandatory
	   ::= { uxos-lioEntry 2 }

uxos-lioSubAddr  OBJECT-TYPE
       SYNTAX DisplayString (SIZE(0..14))
	   ACCESS read-only
	   STATUS mandatory
	   ::= { uxos-lioEntry 3 }

uxos-liocall OBJECT-TYPE
       SYNTAX Counter
	   ACCESS read-only
	   STATUS mandatory
	   ::= { uxos-lioEntry 4 }

uxos-lioread OBJECT-TYPE
       SYNTAX Counter
	   ACCESS read-only
	   STATUS mandatory
	   ::= { uxos-lioEntry 5 }

uxos-liowrite OBJECT-TYPE
       SYNTAX Counter
	   ACCESS read-only
	   STATUS mandatory
	   ::= { uxos-lioEntry 6 }

uxos-liolock OBJECT-TYPE
       SYNTAX Counter
	   ACCESS read-only
	   STATUS mandatory
	   ::= { uxos-lioEntry 7 }

uxos-liopoll OBJECT-TYPE
       SYNTAX Counter
	   ACCESS read-only
	   STATUS mandatory
	   ::= { uxos-lioEntry 8}

uxos-liowait OBJECT-TYPE
       SYNTAX Counter
	   ACCESS read-only
	   STATUS mandatory
	   ::= { uxos-lioEntry 9 }
					   

--...................................................................
-- Ipcinfo group
--...................................................................

uxos-ipcTable OBJECT-TYPE
       SYNTAX SEQUENCE OF IpcEntry
	   ACCESS not-accessible
	   STATUS mandatory
	   ::= { uxos-ipcinfo 1 }

uxos-ipcEntry OBJECT-TYPE
       SYNTAX IpcEntry  
	   ACCESS not-accessible
	   STATUS mandatory
	   INDEX {uxos-ipcSysName,
		  uxos-ipcInstName,
		  uxos-ipcSubAddr}
	   ::= { uxos-ipcTable 1 }

IpcEntry ::= SEQUENCE {
                       uxos-ipcSysName 		DisplayString,
                       uxos-ipcInstName		DisplayString,
                       uxos-ipcSubAddr		DisplayString,
                       uxos-shm-get   		Counter,
                       uxos-shm-get-fail   	Counter,
                       uxos-shm-atch	   	Counter,
                       uxos-shm-atch-fail   	Counter,
                       uxos-shm-dtch	   	Counter,
                       uxos-shm-cntl	   	Counter,
                       uxos-msg-get	   	Counter,
                       uxos-msg-get-fail   	Counter,
                       uxos-msg-snd	   	Counter,
                       uxos-msg-snd-fail   	Counter,
                       uxos-msg-snd-sleep   	Counter,
                       uxos-msg-snd-intr   	Counter,
                       uxos-msg-snd-again   	Counter,
                       uxos-msg-rcv	   	Counter,
                       uxos-msg-rcv-fail   	Counter,
                       uxos-msg-rcv-sleep   	Counter,
                       uxos-msg-rcv-intr   	Counter,
                       uxos-msg-rcv-again   	Counter,
                       uxos-msg-cntl	   	Counter,
                       uxos-msg-lock-sleep 	Counter,
                       uxos-sem-get 		Counter,
                       uxos-sem-get-fail	Counter,
                       uxos-sem-op		Counter,
                       uxos-sem-op-fail   	Counter,
                       uxos-sem-op-sleep   	Counter,
                       uxos-sem-op-intr   	Counter,
                       uxos-sem-op-again   	Counter,
                       uxos-sem-cntl	   	Counter
						}
					   
					   
uxos-ipcSysName OBJECT-TYPE
       SYNTAX DisplayString (SIZE(0..14))
	   ACCESS read-only
	   STATUS mandatory
	   ::= { uxos-ipcEntry 1 }

uxos-ipcInstName OBJECT-TYPE
       SYNTAX DisplayString (SIZE(0..14))
	   ACCESS read-only
	   STATUS mandatory
	   ::= { uxos-ipcEntry 2 }

uxos-ipcSubAddr  OBJECT-TYPE
       SYNTAX DisplayString (SIZE(0..14))
	   ACCESS read-only
	   STATUS mandatory
	   ::= { uxos-ipcEntry 3 }

uxos-shm-get OBJECT-TYPE
       SYNTAX Counter
	   ACCESS read-only
	   STATUS mandatory
	   ::= { uxos-ipcEntry 4 }

uxos-shm-get-fail OBJECT-TYPE
       SYNTAX Counter
	   ACCESS read-only
	   STATUS mandatory
	   ::= { uxos-ipcEntry 5 }

uxos-shm-atch OBJECT-TYPE
       SYNTAX Counter
	   ACCESS read-only
	   STATUS mandatory
	   ::= { uxos-ipcEntry 6 }

uxos-shm-atch-fail OBJECT-TYPE
       SYNTAX Counter
	   ACCESS read-only
	   STATUS mandatory
	   ::= { uxos-ipcEntry 7 }

uxos-shm-dtch OBJECT-TYPE
       SYNTAX Counter
	   ACCESS read-only
	   STATUS mandatory
	   ::= { uxos-ipcEntry 8 }

uxos-shm-cntl OBJECT-TYPE
       SYNTAX Counter
	   ACCESS read-only
	   STATUS mandatory
	   ::= { uxos-ipcEntry 9 }

uxos-msg-get OBJECT-TYPE
       SYNTAX Counter
	   ACCESS read-only
	   STATUS mandatory
	   ::= { uxos-ipcEntry 10 }

uxos-msg-get-fail OBJECT-TYPE
       SYNTAX Counter
	   ACCESS read-only
	   STATUS mandatory
	   ::= { uxos-ipcEntry 11 }

uxos-msg-snd OBJECT-TYPE
       SYNTAX Counter
	   ACCESS read-only
	   STATUS mandatory
	   ::= { uxos-ipcEntry 12 }

uxos-msg-snd-fail OBJECT-TYPE
       SYNTAX Counter
	   ACCESS read-only
	   STATUS mandatory
	   ::= { uxos-ipcEntry 13 }

uxos-msg-snd-sleep OBJECT-TYPE
       SYNTAX Counter
	   ACCESS read-only
	   STATUS mandatory
	   ::= { uxos-ipcEntry 14}

uxos-msg-snd-intr OBJECT-TYPE
       SYNTAX Counter
	   ACCESS read-only
	   STATUS mandatory
	   ::= { uxos-ipcEntry 15 }

uxos-msg-snd-again OBJECT-TYPE
       SYNTAX Counter
	   ACCESS read-only
	   STATUS mandatory
	   ::= { uxos-ipcEntry 16 }

uxos-msg-rcv OBJECT-TYPE
       SYNTAX Counter
	   ACCESS read-only
	   STATUS mandatory
	   ::= { uxos-ipcEntry 17 }

uxos-msg-rcv-fail OBJECT-TYPE
       SYNTAX Counter
	   ACCESS read-only
	   STATUS mandatory
	   ::= { uxos-ipcEntry 18 }

uxos-msg-rcv-sleep OBJECT-TYPE
       SYNTAX Counter
	   ACCESS read-only
	   STATUS mandatory
	   ::= { uxos-ipcEntry 19 }

uxos-msg-rcv-intr OBJECT-TYPE
       SYNTAX Counter
	   ACCESS read-only
	   STATUS mandatory
	   ::= { uxos-ipcEntry 20 }

uxos-msg-rcv-again OBJECT-TYPE
       SYNTAX Counter
	   ACCESS read-only
	   STATUS mandatory
	   ::= { uxos-ipcEntry 21 }

uxos-msg-cntl OBJECT-TYPE
       SYNTAX Counter
	   ACCESS read-only
	   STATUS mandatory
	   ::= { uxos-ipcEntry 22 }

uxos-msg-lock-sleep OBJECT-TYPE
       SYNTAX Counter
	   ACCESS read-only
	   STATUS mandatory
	   ::= { uxos-ipcEntry 23 }

uxos-sem-get OBJECT-TYPE
       SYNTAX Counter
	   ACCESS read-only
	   STATUS mandatory
	   ::= { uxos-ipcEntry 24 }

uxos-sem-get-fail OBJECT-TYPE
       SYNTAX Counter
	   ACCESS read-only
	   STATUS mandatory
	   ::= { uxos-ipcEntry 25 }

uxos-sem-op OBJECT-TYPE
       SYNTAX Counter
	   ACCESS read-only
	   STATUS mandatory
	   ::= { uxos-ipcEntry 26 }

uxos-sem-op-fail OBJECT-TYPE
       SYNTAX Counter
	   ACCESS read-only
	   STATUS mandatory
	   ::= { uxos-ipcEntry 27 }

uxos-sem-op-sleep OBJECT-TYPE
       SYNTAX Counter
	   ACCESS read-only
	   STATUS mandatory
	   ::= { uxos-ipcEntry 28 }

uxos-sem-op-intr OBJECT-TYPE
       SYNTAX Counter
	   ACCESS read-only
	   STATUS mandatory
	   ::= { uxos-ipcEntry 29 }

uxos-sem-op-again OBJECT-TYPE
       SYNTAX Counter
	   ACCESS read-only
	   STATUS mandatory
	   ::= { uxos-ipcEntry 30 }

uxos-sem-cntl OBJECT-TYPE
       SYNTAX Counter
	   ACCESS read-only
	   STATUS mandatory
	   ::= { uxos-ipcEntry 31 }


--...................................................................
-- Flockinfo group
--...................................................................

uxos-flockTable OBJECT-TYPE
       SYNTAX SEQUENCE OF FlockEntry
	   ACCESS not-accessible
	   STATUS mandatory
	   ::= { uxos-flockinfo 1 }

uxos-flockEntry OBJECT-TYPE
       SYNTAX FlockEntry  
	   ACCESS not-accessible
	   STATUS mandatory
	   INDEX {uxos-flockSysName,
		  uxos-flockInstName,
		  uxos-flockSubAddr}
	   ::= { uxos-flockTable 1 }

FlockEntry ::= SEQUENCE {
                       uxos-flockSysName 	DisplayString,
                       uxos-flockInstName	DisplayString,
                       uxos-flockSubAddr	DisplayString,
                       uxos-lock-read  		Counter,
                       uxos-lock-rd-fail   	Counter,
                       uxos-lock-rd-sleep   	Counter,
                       uxos-lock-rd-intr   	Counter,
                       uxos-lock-rd-again   	Counter,
                       uxos-lock-write 		Counter,
                       uxos-lock-wr-fail   	Counter,
                       uxos-lock-wr-sleep   	Counter,
                       uxos-lock-wr-intr   	Counter,
                       uxos-lock-wr-again   	Counter,
                       uxos-unlock	   	Counter
						}
					   
uxos-flockSysName OBJECT-TYPE
       SYNTAX DisplayString (SIZE(0..14))
	   ACCESS read-only
	   STATUS mandatory
	   ::= { uxos-flockEntry 1 }
					   
uxos-flockInstName OBJECT-TYPE
       SYNTAX DisplayString (SIZE(0..14))
	   ACCESS read-only
	   STATUS mandatory
	   ::= { uxos-flockEntry 2 }

uxos-flockSubAddr  OBJECT-TYPE
       SYNTAX DisplayString (SIZE(0..14))
	   ACCESS read-only
	   STATUS mandatory
	   ::= { uxos-flockEntry 3 }

uxos-lock-read OBJECT-TYPE
       SYNTAX Counter
	   ACCESS read-only
	   STATUS mandatory
	   ::= { uxos-flockEntry 4 }

uxos-lock-rd-fail OBJECT-TYPE
       SYNTAX Counter
	   ACCESS read-only
	   STATUS mandatory
	   ::= { uxos-flockEntry 5 }

uxos-lock-rd-sleep OBJECT-TYPE
       SYNTAX Counter
	   ACCESS read-only
	   STATUS mandatory
	   ::= { uxos-flockEntry 6 }

uxos-lock-rd-intr OBJECT-TYPE
       SYNTAX Counter
	   ACCESS read-only
	   STATUS mandatory
	   ::= { uxos-flockEntry 7 }

uxos-lock-rd-again OBJECT-TYPE
       SYNTAX Counter
	   ACCESS read-only
	   STATUS mandatory
	   ::= { uxos-flockEntry 8 }

uxos-lock-write OBJECT-TYPE
       SYNTAX Counter
	   ACCESS read-only
	   STATUS mandatory
	   ::= { uxos-flockEntry 9 }

uxos-lock-wr-fail OBJECT-TYPE
       SYNTAX Counter
	   ACCESS read-only
	   STATUS mandatory
	   ::= { uxos-flockEntry 10 }

uxos-lock-wr-sleep OBJECT-TYPE
       SYNTAX Counter
	   ACCESS read-only
	   STATUS mandatory
	   ::= { uxos-flockEntry 11 }

uxos-lock-wr-intr OBJECT-TYPE
       SYNTAX Counter
	   ACCESS read-only
	   STATUS mandatory
	   ::= { uxos-flockEntry 12 }

uxos-lock-wr-again OBJECT-TYPE
       SYNTAX Counter
	   ACCESS read-only
	   STATUS mandatory
	   ::= { uxos-flockEntry 13 }

uxos-unlock OBJECT-TYPE
       SYNTAX Counter
	   ACCESS read-only
	   STATUS mandatory
	   ::= { uxos-flockEntry 14 }


--...................................................................
-- Segminfo group
--...................................................................

uxos-smTable OBJECT-TYPE
       SYNTAX SEQUENCE OF SmEntry
	   ACCESS not-accessible
	   STATUS mandatory
	   ::= { uxos-segminfo 1 }

uxos-smEntry OBJECT-TYPE
       SYNTAX SmEntry  
	   ACCESS not-accessible
	   STATUS mandatory
	   INDEX {uxos-smSysName,
		  uxos-smInstName,
		  uxos-smSubAddr}
	   ::= { uxos-smTable 1 }

SmEntry ::= SEQUENCE {
                       uxos-smSysName 		DisplayString,
                       uxos-smInstName		DisplayString,
                       uxos-smSubAddr		DisplayString,
                       uxos-fault   		Counter,
                       uxos-faulta   		Counter,
                       uxos-getmap   		Counter,
                       uxos-get-use   		Counter,
                       uxos-get-reclaim	 	Counter,
                       uxos-get-reuse  	 	Counter,
                       uxos-rel-async		Counter,
                       uxos-rel-write		Counter,
                       uxos-rel-free   		Counter,
                       uxos-rel-abort		Counter,
                       uxos-rel-dontneed   	Counter,
                       uxos-release   		Counter,
                       uxos-pagecreate   	Counter,
                       uxos-pagemiss 	  	Counter,
                       uxos-pagemissatch   	Counter
						}
					   
					   
uxos-smSysName OBJECT-TYPE
       SYNTAX DisplayString (SIZE(0..14))
	   ACCESS read-only
	   STATUS mandatory
	   ::= { uxos-smEntry 1 }

uxos-smInstName OBJECT-TYPE
       SYNTAX DisplayString (SIZE(0..14))
	   ACCESS read-only
	   STATUS mandatory
	   ::= { uxos-smEntry 2 }

uxos-smSubAddr  OBJECT-TYPE
       SYNTAX DisplayString (SIZE(0..14))
	   ACCESS read-only
	   STATUS mandatory
	   ::= { uxos-smEntry 3 }

uxos-fault OBJECT-TYPE
       SYNTAX Counter
	   ACCESS read-only
	   STATUS mandatory
	   ::= { uxos-smEntry 4 }

uxos-faulta OBJECT-TYPE
       SYNTAX Counter
	   ACCESS read-only
	   STATUS mandatory
	   ::= { uxos-smEntry 5 }

uxos-getmap OBJECT-TYPE
       SYNTAX Counter
	   ACCESS read-only
	   STATUS mandatory
	   ::= { uxos-smEntry 6 }

uxos-get-use OBJECT-TYPE
       SYNTAX Counter
	   ACCESS read-only
	   STATUS mandatory
	   ::= { uxos-smEntry 7 }

uxos-get-reclaim OBJECT-TYPE
       SYNTAX Counter
	   ACCESS read-only
	   STATUS mandatory
	   ::= { uxos-smEntry 8 }

uxos-get-reuse OBJECT-TYPE
       SYNTAX Counter
	   ACCESS read-only
	   STATUS mandatory
	   ::= { uxos-smEntry 9 }

uxos-rel-async OBJECT-TYPE
       SYNTAX Counter
	   ACCESS read-only
	   STATUS mandatory
	   ::= { uxos-smEntry 10 }

uxos-rel-write OBJECT-TYPE
       SYNTAX Counter
	   ACCESS read-only
	   STATUS mandatory
	   ::= { uxos-smEntry 11 }

uxos-rel-free OBJECT-TYPE
       SYNTAX Counter
	   ACCESS read-only
	   STATUS mandatory
	   ::= { uxos-smEntry 12 }

uxos-rel-abort OBJECT-TYPE
       SYNTAX Counter
	   ACCESS read-only
	   STATUS mandatory
	   ::= { uxos-smEntry 13 }

uxos-rel-dontneed OBJECT-TYPE
       SYNTAX Counter
	   ACCESS read-only
	   STATUS mandatory
	   ::= { uxos-smEntry 14 }

uxos-release OBJECT-TYPE
       SYNTAX Counter
	   ACCESS read-only
	   STATUS mandatory
	   ::= { uxos-smEntry 15 }

uxos-pagecreate OBJECT-TYPE
       SYNTAX Counter
	   ACCESS read-only
	   STATUS mandatory
	   ::= { uxos-smEntry 16 }

uxos-pagemiss OBJECT-TYPE
       SYNTAX Counter
	   ACCESS read-only
	   STATUS mandatory
	   ::= { uxos-smEntry 17 }

uxos-pagemissatch OBJECT-TYPE
       SYNTAX Counter
	   ACCESS read-only
	   STATUS mandatory
	   ::= { uxos-smEntry 18 }


--...................................................................
-- Vxinfo group
--...................................................................

uxos-vxTable OBJECT-TYPE
       SYNTAX SEQUENCE OF VxEntry
	   ACCESS not-accessible
	   STATUS mandatory
	   ::= { uxos-vxinfo 1 }

uxos-vxEntry OBJECT-TYPE
       SYNTAX VxEntry  
	   ACCESS not-accessible
	   STATUS mandatory
	   INDEX {uxos-vxSysName,
		  uxos-vxInstName,
		  uxos-vxSubAddr}
	   ::= { uxos-vxTable 1 }

VxEntry ::= SEQUENCE {
                       uxos-vxSysName 	DisplayString,
                       uxos-vxInstName	DisplayString,
                       uxos-vxSubAddr	DisplayString,
                       uxos-vxipage   	Counter,
                       uxos-vxinopage  	Counter,
                       uxos-vxinodeovf 	Counter
					}

uxos-vxSysName OBJECT-TYPE
       SYNTAX DisplayString (SIZE(0..14))
	   ACCESS read-only
	   STATUS mandatory
	   ::= { uxos-vxEntry 1 }

uxos-vxInstName OBJECT-TYPE
       SYNTAX DisplayString (SIZE(0..14))
	   ACCESS read-only
	   STATUS mandatory
	   ::= { uxos-vxEntry 2 }

uxos-vxSubAddr  OBJECT-TYPE
       SYNTAX DisplayString (SIZE(0..14))
	   ACCESS read-only
	   STATUS mandatory
	   ::= { uxos-vxEntry 3 }

uxos-vxipage OBJECT-TYPE
       SYNTAX Counter
	   ACCESS read-only
	   STATUS mandatory
	   ::= { uxos-vxEntry 4 }

uxos-vxinopage OBJECT-TYPE
       SYNTAX Counter
	   ACCESS read-only
	   STATUS mandatory
	   ::= { uxos-vxEntry 5 }

uxos-vxinodeovf OBJECT-TYPE
       SYNTAX Counter
	   ACCESS read-only
	   STATUS mandatory
	   ::= { uxos-vxEntry 6 }

 --...................................................................
 -- Scsi group
 --...................................................................

uxos-diskTable   OBJECT-TYPE
       SYNTAX SEQUENCE OF DiskEntry
	   ACCESS not-accessible
	   STATUS mandatory
	   ::= { uxos-scsi 1 }

uxos-diskEntry   OBJECT-TYPE
       SYNTAX DiskEntry
	   ACCESS not-accessible
	   STATUS mandatory
	   INDEX {uxos-diskSysName,
		  uxos-diskInstName,
		  uxos-diskSubAddr}
	   ::= { uxos-diskTable 1 }

DiskEntry ::= SEQUENCE {
                       uxos-diskSysName 	DisplayString,
                       uxos-diskInstName 	DisplayString,
                       uxos-diskSubAddr 	DisplayString,
                       uxos-numRW 	    	Counter,
                       uxos-numOtherOp   	Counter,
                       uxos-numJobsToDr 	Counter,
                       uxos-numUnlogErr 	Counter,
                       uxos-totBlkTrans		Counter,
                       uxos-totBlkResp		Counter,
                       uxos-cumulUse		Counter,
                       uxos-major		Counter,
                       uxos-minor		Counter,
                       uxos-totNumRead		Counter,
                       uxos-totNumWrite		Counter,
                       uxos-cumulQueLen		Counter,
                       uxos-maxQueLen		Counter,
                       uxos-minQueLen		Counter,
                       uxos-cumulSeekDist	Counter,
                       uxos-driveActive		Counter,
                       uxos-drivePerf		Counter,
                       uxos-startOfQueue	INTEGER,
                       uxos-lastInQueue		INTEGER,
                       uxos-queue01		INTEGER,
                       uxos-queue02		INTEGER,
                       uxos-queue11		INTEGER,
                       uxos-queue12		INTEGER,
                       uxos-queue21		INTEGER,
                       uxos-queue22		INTEGER,
                       uxos-queue31		INTEGER,
                       uxos-queue32		INTEGER,
                       uxos-queue41		INTEGER,
                       uxos-queue42		INTEGER,
                       uxos-queue51		INTEGER,
                       uxos-queue52		INTEGER,
                       uxos-queue61		INTEGER,
                       uxos-queue62		INTEGER,
                       uxos-queue71		INTEGER,
                       uxos-queue72		INTEGER,
                       uxos-queue81		INTEGER,
                       uxos-queue82		INTEGER,
                       uxos-queue91		INTEGER,
                       uxos-queue92		INTEGER
					   }
					   
uxos-diskSysName OBJECT-TYPE
           SYNTAX DisplayString (SIZE(0..14))
	   ACCESS read-only
	   STATUS mandatory
	   ::= { uxos-diskEntry 1 }

uxos-diskInstName OBJECT-TYPE
           SYNTAX DisplayString (SIZE(0..14))
	   ACCESS read-only
	   STATUS mandatory
	   ::= { uxos-diskEntry 2 }

uxos-diskSubAddr  OBJECT-TYPE
           SYNTAX DisplayString (SIZE(0..16))
	   ACCESS read-only
	   STATUS mandatory
	   ::= { uxos-diskEntry 3 }

uxos-numRW   OBJECT-TYPE
	   SYNTAX Counter
	   ACCESS read-only 
       	   STATUS mandatory
	   ::= { uxos-diskEntry 4 }    

uxos-numOtherOp   OBJECT-TYPE
	   SYNTAX Counter
	   ACCESS read-only 
       	   STATUS mandatory
	   ::= { uxos-diskEntry 5 }    

uxos-numJobsToDr   OBJECT-TYPE
	   SYNTAX Counter
	   ACCESS read-only 
       	   STATUS mandatory
	   ::= { uxos-diskEntry 6 }    

uxos-numUnlogErr   OBJECT-TYPE
	   SYNTAX Counter
	   ACCESS read-only 
       	   STATUS mandatory
	   ::= { uxos-diskEntry 7 }    

uxos-totBlkTrans   OBJECT-TYPE
	   SYNTAX Counter
	   ACCESS read-only 
       	   STATUS mandatory
	   ::= { uxos-diskEntry 8 }    

uxos-totBlkResp   OBJECT-TYPE
	   SYNTAX Counter
	   ACCESS read-only 
       	   STATUS mandatory
	   ::= { uxos-diskEntry 9 }    

uxos-cumulUse   OBJECT-TYPE
	   SYNTAX Counter
	   ACCESS read-only 
       	   STATUS mandatory
	   ::= { uxos-diskEntry 10 }    

uxos-major   OBJECT-TYPE
	   SYNTAX Counter
	   ACCESS read-only 
       	   STATUS mandatory
	   ::= { uxos-diskEntry 11 }    

uxos-minor   OBJECT-TYPE
	   SYNTAX Counter
	   ACCESS read-only 
       	   STATUS mandatory
	   ::= { uxos-diskEntry 12 }    

uxos-totNumRead   OBJECT-TYPE
	   SYNTAX Counter
	   ACCESS read-only 
       	   STATUS mandatory
	   ::= { uxos-diskEntry 13 }    

uxos-totNumWrite   OBJECT-TYPE
	   SYNTAX Counter
	   ACCESS read-only 
       	   STATUS mandatory
	   ::= { uxos-diskEntry 14 }    

uxos-cumulQueLen   OBJECT-TYPE
	   SYNTAX Counter
	   ACCESS read-only 
       	   STATUS mandatory
	   ::= { uxos-diskEntry 15 }    

uxos-maxQueLen   OBJECT-TYPE
	   SYNTAX Counter
	   ACCESS read-only 
       	   STATUS mandatory
	   ::= { uxos-diskEntry 16 }    

uxos-minQueLen   OBJECT-TYPE
	   SYNTAX Counter
	   ACCESS read-only 
       	   STATUS mandatory
	   ::= { uxos-diskEntry 17 }    

uxos-cumulSeekDist   OBJECT-TYPE
	   SYNTAX Counter
	   ACCESS read-only 
       	   STATUS mandatory
	   ::= { uxos-diskEntry 18 }    

uxos-driveActive   OBJECT-TYPE
	   SYNTAX Counter
	   ACCESS read-only 
       	   STATUS mandatory
	   ::= { uxos-diskEntry 19 }    

uxos-drivePerf   OBJECT-TYPE
	   SYNTAX Counter
	   ACCESS read-only 
       	   STATUS mandatory
	   ::= { uxos-diskEntry 20 }    

uxos-startOfQueue   OBJECT-TYPE
	   SYNTAX INTEGER
	   ACCESS read-only 
       	   STATUS mandatory
	   ::= { uxos-diskEntry 21 }    

uxos-lastInQueue   OBJECT-TYPE
	   SYNTAX INTEGER
	   ACCESS read-only 
       	   STATUS mandatory
	   ::= { uxos-diskEntry 22 }    

uxos-queue01   OBJECT-TYPE
	   SYNTAX INTEGER
	   ACCESS read-only 
       	   STATUS mandatory
	   ::= { uxos-diskEntry 23 }    

uxos-queue02   OBJECT-TYPE
	   SYNTAX INTEGER
	   ACCESS read-only 
       	   STATUS mandatory
	   ::= { uxos-diskEntry 24 }    

uxos-queue11   OBJECT-TYPE
	   SYNTAX INTEGER
	   ACCESS read-only 
       	   STATUS mandatory
	   ::= { uxos-diskEntry 25 }    

uxos-queue12   OBJECT-TYPE
	   SYNTAX INTEGER
	   ACCESS read-only 
       	   STATUS mandatory
	   ::= { uxos-diskEntry 26 }    

uxos-queue21   OBJECT-TYPE
	   SYNTAX INTEGER
	   ACCESS read-only 
       	   STATUS mandatory
	   ::= { uxos-diskEntry 27 }    

uxos-queue22   OBJECT-TYPE
	   SYNTAX INTEGER
	   ACCESS read-only 
       	   STATUS mandatory
	   ::= { uxos-diskEntry 28 }    

uxos-queue31   OBJECT-TYPE
	   SYNTAX INTEGER
	   ACCESS read-only 
       	   STATUS mandatory
	   ::= { uxos-diskEntry 29 }    

uxos-queue32   OBJECT-TYPE
	   SYNTAX INTEGER
	   ACCESS read-only 
       	   STATUS mandatory
	   ::= { uxos-diskEntry 30 }    

uxos-queue41   OBJECT-TYPE
	   SYNTAX INTEGER
	   ACCESS read-only 
       	   STATUS mandatory
	   ::= { uxos-diskEntry 31 }    

uxos-queue42   OBJECT-TYPE
	   SYNTAX INTEGER
	   ACCESS read-only 
       	   STATUS mandatory
	   ::= { uxos-diskEntry 32 }    

uxos-queue51   OBJECT-TYPE
	   SYNTAX INTEGER
	   ACCESS read-only 
       	   STATUS mandatory
	   ::= { uxos-diskEntry 33 }    

uxos-queue52   OBJECT-TYPE
	   SYNTAX INTEGER
	   ACCESS read-only 
       	   STATUS mandatory
	   ::= { uxos-diskEntry 34 }    

uxos-queue61   OBJECT-TYPE
	   SYNTAX INTEGER
	   ACCESS read-only 
       	   STATUS mandatory
	   ::= { uxos-diskEntry 35 }    

uxos-queue62   OBJECT-TYPE
	   SYNTAX INTEGER
	   ACCESS read-only 
       	   STATUS mandatory
	   ::= { uxos-diskEntry 36 }    

uxos-queue71   OBJECT-TYPE
	   SYNTAX INTEGER
	   ACCESS read-only 
       	   STATUS mandatory
	   ::= { uxos-diskEntry 37 }    

uxos-queue72   OBJECT-TYPE
	   SYNTAX INTEGER
	   ACCESS read-only 
       	   STATUS mandatory
	   ::= { uxos-diskEntry 38 }    

uxos-queue81   OBJECT-TYPE
	   SYNTAX INTEGER
	   ACCESS read-only 
       	   STATUS mandatory
	   ::= { uxos-diskEntry 39 }    

uxos-queue82   OBJECT-TYPE
	   SYNTAX INTEGER
	   ACCESS read-only 
       	   STATUS mandatory
	   ::= { uxos-diskEntry 40 }    

uxos-queue91   OBJECT-TYPE
	   SYNTAX INTEGER
	   ACCESS read-only 
       	   STATUS mandatory
	   ::= { uxos-diskEntry 41 }    

uxos-queue92   OBJECT-TYPE
	   SYNTAX INTEGER
	   ACCESS read-only 
       	   STATUS mandatory
	   ::= { uxos-diskEntry 42 }    

-- WAN DEFINITIONS ::= BEGIN
-- 
-- IMPORTS
--     enterprises,OBJECT-TYPE
-- 	    FROM RFC1155-SMI;
-- 
-- 
wan     OBJECT IDENTIFIER ::= { lsx-unix 15}

lapb      OBJECT IDENTIFIER ::= { wan 2 }
x25       OBJECT IDENTIFIER ::= { wan 3 }
tp02      OBJECT IDENTIFIER ::= { wan 4 }


lapbTable    OBJECT-TYPE
       SYNTAX SEQUENCE OF LapbEntry
	   ACCESS not-accessible
	   STATUS mandatory
	   ::= { lapb 1 }

lapbEntry    OBJECT-TYPE
       SYNTAX LapbEntry  
	   ACCESS not-accessible
	   STATUS mandatory
	   INDEX  { uxlapb-lapbSysName,
		    uxlapb-lapbInstName,
		    uxlapb-lapbSubAddr }
	   ::= { lapbTable 1 }

LapbEntry ::= SEQUENCE {
                       uxlapb-lapbSysName DisplayString,
                       uxlapb-lapbInstName DisplayString,
                       uxlapb-lapbSubAddr DisplayString,
                       uxlapb-numOfzerotime  Counter,
                       uxlapb-numOfinfosent  Counter,
                       uxlapb-numOfinforece  Counter,
                       uxlapb-numOfrrsent  Counter,
                       uxlapb-numOfrrrece  Counter,
                       uxlapb-numOfrnrsent  Counter,
                       uxlapb-numOfrnrrece  Counter,
                       uxlapb-numOfSABMitsent  Counter,
                       uxlapb-numOfSABMnitsent  Counter,
                       uxlapb-numOfSABMitrece  Counter,
                       uxlapb-numOfSABMnitrece  Counter,
                       uxlapb-numOfDISCitsent  Counter,
                       uxlapb-numOfDISCnitsent  Counter,
                       uxlapb-numOfDISCitrece  Counter,
                       uxlapb-numOfDISCnitrece  Counter,
                       uxlapb-numOfUAitsent  Counter,
                       uxlapb-numOfUAnitsent  Counter,
                       uxlapb-numOfUAitrece  Counter,
                       uxlapb-numOfUAnitrece  Counter,
                       uxlapb-numOfDMitsent  Counter,
                       uxlapb-numOfDMnitsent  Counter,
                       uxlapb-numOfDMitrece  Counter,
                       uxlapb-numOfDMnitrece  Counter,
                       uxlapb-numOffrmrsent  Counter,
                       uxlapb-numOffrmrrece  Counter,
                       uxlapb-numOfrejsent  Counter,
                       uxlapb-numOfrejrece  Counter,
                       uxlapb-numOfbusycondet  Counter, 
                       uxlapb-numOfbusyconent  Counter, 
                       uxlapb-numOfdataoctsent  Counter,
                       uxlapb-numOfdataoctrece  Counter,
                       uxlapb-numOfoutsequence  Counter,
                       uxlapb-numOfretrframes  Counter,
                       uxlapb-numOfinvalidframes  Counter,
                       uxlapb-numOfphystxerrors  Counter,
                       uxlapb-numOfReserved1  Counter,
                       uxlapb-numOfReserved2  Counter,
                       uxlapb-numOfReserved3  Counter,
                       uxlapb-numOfReserved4  Counter,
                       uxlapb-numOfInformatype  Counter
					   }

uxlapb-lapbSysName OBJECT-TYPE
       SYNTAX DisplayString (SIZE(0..16))
	   ACCESS read-only
	   STATUS mandatory
	   ::= { lapbEntry 1 }

					   
uxlapb-lapbInstName OBJECT-TYPE
       SYNTAX DisplayString (SIZE(0..14))
	   ACCESS read-only
	   STATUS mandatory
	   ::= { lapbEntry 2 }

uxlapb-lapbSubAddr  OBJECT-TYPE
       SYNTAX DisplayString (SIZE(0..16))
	   ACCESS read-only
	   STATUS mandatory
	   ::= { lapbEntry 3 }

uxlapb-numOfzerotime  OBJECT-TYPE
       SYNTAX Counter
	   ACCESS read-only
	   STATUS mandatory
	   ::= { lapbEntry 4 }

uxlapb-numOfinfosent  OBJECT-TYPE
       SYNTAX Counter
	   ACCESS read-only
	   STATUS mandatory
	   ::= { lapbEntry 5 }

uxlapb-numOfinforece  OBJECT-TYPE
       SYNTAX Counter
	   ACCESS read-only
	   STATUS mandatory
	   ::= { lapbEntry 6 }

uxlapb-numOfrrsent  OBJECT-TYPE
       SYNTAX Counter
	   ACCESS read-only
	   STATUS mandatory
	   ::= { lapbEntry 7 }

uxlapb-numOfrrrece  OBJECT-TYPE
       SYNTAX Counter
	   ACCESS read-only
	   STATUS mandatory
	   ::= { lapbEntry 8 }

uxlapb-numOfrnrsent  OBJECT-TYPE
       SYNTAX Counter
	   ACCESS read-only
	   STATUS mandatory
	   ::= { lapbEntry 9 }

uxlapb-numOfrnrrece  OBJECT-TYPE
       SYNTAX Counter
	   ACCESS read-only
	   STATUS mandatory
	   ::= { lapbEntry 10 }

uxlapb-numOfSABMitsent  OBJECT-TYPE
       SYNTAX Counter
	   ACCESS read-only
	   STATUS mandatory
	   ::= { lapbEntry 11 }

uxlapb-numOfSABMnitsent  OBJECT-TYPE
       SYNTAX Counter
	   ACCESS read-only
	   STATUS mandatory
	   ::= { lapbEntry 12 }

uxlapb-numOfSABMitrece  OBJECT-TYPE
       SYNTAX Counter
	   ACCESS read-only
	   STATUS mandatory
	   ::= { lapbEntry 13 }

uxlapb-numOfSABMnitrece  OBJECT-TYPE
       SYNTAX Counter
	   ACCESS read-only
	   STATUS mandatory
	   ::= { lapbEntry 14 }

uxlapb-numOfDISCitsent  OBJECT-TYPE
       SYNTAX Counter
	   ACCESS read-only
	   STATUS mandatory
	   ::= { lapbEntry 15 }

uxlapb-numOfDISCnitsent  OBJECT-TYPE
       SYNTAX Counter
	   ACCESS read-only
	   STATUS mandatory
	   ::= { lapbEntry 16 }

uxlapb-numOfDISCitrece  OBJECT-TYPE
       SYNTAX Counter
	   ACCESS read-only
	   STATUS mandatory
	   ::= { lapbEntry 17 }

uxlapb-numOfDISCnitrece  OBJECT-TYPE
       SYNTAX Counter
	   ACCESS read-only
	   STATUS mandatory
	   ::= { lapbEntry 18 }

uxlapb-numOfUAitsent  OBJECT-TYPE
       SYNTAX Counter
	   ACCESS read-only
	   STATUS mandatory
	   ::= { lapbEntry 19 }

uxlapb-numOfUAnitsent  OBJECT-TYPE
       SYNTAX Counter
	   ACCESS read-only
	   STATUS mandatory
	   ::= { lapbEntry 20 }

uxlapb-numOfUAitrece  OBJECT-TYPE
       SYNTAX Counter
	   ACCESS read-only
	   STATUS mandatory
	   ::= { lapbEntry 21 }

uxlapb-numOfUAnitrece  OBJECT-TYPE
       SYNTAX Counter
	   ACCESS read-only
	   STATUS mandatory
	   ::= { lapbEntry 22 }

uxlapb-numOfDMitsent  OBJECT-TYPE
       SYNTAX Counter
	   ACCESS read-only
	   STATUS mandatory
	   ::= { lapbEntry 23 }

uxlapb-numOfDMnitsent  OBJECT-TYPE
       SYNTAX Counter
	   ACCESS read-only
	   STATUS mandatory
	   ::= { lapbEntry 24 }

uxlapb-numOfDMitrece  OBJECT-TYPE
       SYNTAX Counter
	   ACCESS read-only
	   STATUS mandatory
	   ::= { lapbEntry 25 }

uxlapb-numOfDMnitrece  OBJECT-TYPE
       SYNTAX Counter
	   ACCESS read-only
	   STATUS mandatory
	   ::= { lapbEntry 26 }

uxlapb-numOffrmrsent  OBJECT-TYPE
       SYNTAX Counter
	   ACCESS read-only
	   STATUS mandatory
	   ::= { lapbEntry 27 }

uxlapb-numOffrmrrece  OBJECT-TYPE
       SYNTAX Counter
	   ACCESS read-only
	   STATUS mandatory
	   ::= { lapbEntry 28 }

uxlapb-numOfrejsent  OBJECT-TYPE
       SYNTAX Counter
	   ACCESS read-only
	   STATUS mandatory
	   ::= { lapbEntry 29 }

uxlapb-numOfrejrece  OBJECT-TYPE
       SYNTAX Counter
	   ACCESS read-only
	   STATUS mandatory
	   ::= { lapbEntry 30 }

uxlapb-numOfbusycondet  OBJECT-TYPE
       SYNTAX Counter
	   ACCESS read-only
	   STATUS mandatory
	   ::= { lapbEntry 31 }

uxlapb-numOfbusyconent  OBJECT-TYPE
       SYNTAX Counter
	   ACCESS read-only
	   STATUS mandatory
	   ::= { lapbEntry 32 }

uxlapb-numOfdataoctsent  OBJECT-TYPE
       SYNTAX Counter
	   ACCESS read-only
	   STATUS mandatory
	   ::= { lapbEntry 33 }

uxlapb-numOfdataoctrece  OBJECT-TYPE
       SYNTAX Counter
	   ACCESS read-only
	   STATUS mandatory
	   ::= { lapbEntry 34 }

uxlapb-numOfoutsequence  OBJECT-TYPE
       SYNTAX Counter
	   ACCESS read-only
	   STATUS mandatory
	   ::= { lapbEntry 35 }

uxlapb-numOfretrframes  OBJECT-TYPE
       SYNTAX Counter
	   ACCESS read-only
	   STATUS mandatory
	   ::= { lapbEntry 36 }

uxlapb-numOfinvalidframes  OBJECT-TYPE
       SYNTAX Counter
	   ACCESS read-only
	   STATUS mandatory
	   ::= { lapbEntry 37 }

uxlapb-numOfphystxerrors  OBJECT-TYPE
       SYNTAX Counter
	   ACCESS read-only
	   STATUS mandatory
	   ::= { lapbEntry 38 }

uxlapb-numOfReserved1  OBJECT-TYPE
       SYNTAX Counter
	   ACCESS read-only
	   STATUS mandatory
	   ::= { lapbEntry 39 }

uxlapb-numOfReserved2  OBJECT-TYPE
       SYNTAX Counter
	   ACCESS read-only
	   STATUS mandatory
	   ::= { lapbEntry 40 }

uxlapb-numOfReserved3  OBJECT-TYPE
       SYNTAX Counter
	   ACCESS read-only
	   STATUS mandatory
	   ::= { lapbEntry 41 }

uxlapb-numOfReserved4  OBJECT-TYPE
       SYNTAX Counter
	   ACCESS read-only
	   STATUS mandatory
	   ::= { lapbEntry 42 }

uxlapb-numOfInformatype  OBJECT-TYPE
       SYNTAX Counter
	   ACCESS read-only
	   STATUS mandatory
	   ::= { lapbEntry 43 }

 --...................................................................
 --...................................................................

x25Table    OBJECT-TYPE
       SYNTAX SEQUENCE OF X25Entry
	   ACCESS not-accessible
	   STATUS mandatory
	   ::= { x25 1 }

x25Entry    OBJECT-TYPE
       SYNTAX X25Entry  
	   ACCESS not-accessible
	   STATUS mandatory
	   INDEX  { uxx25-x25SysName,
	            uxx25-x25InstName,
		    uxx25-x25SubAddr }
	   ::= { x25Table 1 }

X25Entry ::= SEQUENCE {
                       uxx25-x25SysName DisplayString,
                       uxx25-x25InstName DisplayString,
                       uxx25-x25SubAddr DisplayString,
                       uxx25-numOfzerot  Counter,
                       uxx25-numOfrestsent  Counter,
                       uxx25-numOfrestrece  Counter,
                       uxx25-numOfcallsent  Counter,
                       uxx25-numOfcallrece  Counter,
                       uxx25-numOfclearsent  Counter,
                       uxx25-numOfclearrece  Counter,
                       uxx25-numOfdatasent  Counter,
                       uxx25-numOfdatarece  Counter,
                       uxx25-numOfoctsent  Counter,
                       uxx25-numOfoctrece  Counter,
                       uxx25-numOfintersent  Counter,
                       uxx25-numOfinterrece  Counter,
                       uxx25-numOfrrxsent  Counter,
                       uxx25-numOfrrxrece  Counter,
                       uxx25-numOfrnrxsent  Counter,
                       uxx25-numOfrnrxrece  Counter,
                       uxx25-numOfresetsent  Counter, 
                       uxx25-numOfresetrece  Counter, 
                       uxx25-numOfrejxsent  Counter, 
                       uxx25-numOfrejxrece  Counter, 
                       uxx25-numOfdiagnsent  Counter,
                       uxx25-numOfdiagnrece  Counter,
                       uxx25-numOfregistsent  Counter,
                       uxx25-numOfregistrece  Counter,
                       uxx25-numOfrestretries  Counter, 
                       uxx25-numOfrestunsucfull  Counter, 
                       uxx25-numOfsyntaxerrors  Counter,
                       uxx25-numOflogicalerrors  Counter,
                       uxx25-numOfcallunsucfull  Counter, 
                       uxx25-numOfclearretries  Counter,
                       uxx25-numOfclearunsucfull  Counter, 
                       uxx25-numOfinterunsucfull  Counter, 
                       uxx25-numOfresetretries  Counter,
                       uxx25-numOfresetunsucfull  Counter, 
                       uxx25-numOfdataretrsucfull  Counter, 
                       uxx25-numOfdataretrunsucfull  Counter, 
                       uxx25-numOfrejretries  Counter,
                       uxx25-numOfrejunsucfull  Counter, 
                       uxx25-numOfInformat  Counter
					   }

					   
uxx25-x25SysName OBJECT-TYPE
       SYNTAX DisplayString (SIZE(0..16))
	   ACCESS read-only
	   STATUS mandatory
	   ::= { x25Entry 1 }
					   
uxx25-x25InstName OBJECT-TYPE
       SYNTAX DisplayString (SIZE(0..14))
	   ACCESS read-only
	   STATUS mandatory
	   ::= { x25Entry 2 }

uxx25-x25SubAddr  OBJECT-TYPE
       SYNTAX DisplayString (SIZE(0..16))
	   ACCESS read-only
	   STATUS mandatory
	   ::= { x25Entry 3 }

uxx25-numOfzerot  OBJECT-TYPE
       SYNTAX Counter
	   ACCESS read-only
	   STATUS mandatory
	   ::= { x25Entry 4 }

uxx25-numOfrestsent  OBJECT-TYPE
       SYNTAX Counter
	   ACCESS read-only
	   STATUS mandatory
	   ::= { x25Entry 5 }

uxx25-numOfrestrece  OBJECT-TYPE
       SYNTAX Counter
	   ACCESS read-only
	   STATUS mandatory
	   ::= { x25Entry 6 }

uxx25-numOfcallsent  OBJECT-TYPE
       SYNTAX Counter
	   ACCESS read-only
	   STATUS mandatory
	   ::= { x25Entry 7 }

uxx25-numOfcallrece  OBJECT-TYPE
       SYNTAX Counter
	   ACCESS read-only
	   STATUS mandatory
	   ::= { x25Entry 8 }

uxx25-numOfclearsent  OBJECT-TYPE
       SYNTAX Counter
	   ACCESS read-only
	   STATUS mandatory
	   ::= { x25Entry 9 }

uxx25-numOfclearrece  OBJECT-TYPE
       SYNTAX Counter
	   ACCESS read-only
	   STATUS mandatory
	   ::= { x25Entry 10 }

uxx25-numOfdatasent  OBJECT-TYPE
       SYNTAX Counter
	   ACCESS read-only
	   STATUS mandatory
	   ::= { x25Entry 11 }

uxx25-numOfdatarece  OBJECT-TYPE
       SYNTAX Counter
	   ACCESS read-only
	   STATUS mandatory
	   ::= { x25Entry 12 }

uxx25-numOfoctsent  OBJECT-TYPE
       SYNTAX Counter
	   ACCESS read-only
	   STATUS mandatory
	   ::= { x25Entry 13 }

uxx25-numOfoctrece  OBJECT-TYPE
       SYNTAX Counter
	   ACCESS read-only
	   STATUS mandatory
	   ::= { x25Entry 14 }

uxx25-numOfintersent  OBJECT-TYPE
       SYNTAX Counter
	   ACCESS read-only
	   STATUS mandatory
	   ::= { x25Entry 15 }

uxx25-numOfinterrece  OBJECT-TYPE
       SYNTAX Counter
	   ACCESS read-only
	   STATUS mandatory
	   ::= { x25Entry 16 }

uxx25-numOfrrxsent  OBJECT-TYPE
       SYNTAX Counter
	   ACCESS read-only
	   STATUS mandatory
	   ::= { x25Entry 17 }

uxx25-numOfrrxrece  OBJECT-TYPE
       SYNTAX Counter
	   ACCESS read-only
	   STATUS mandatory
	   ::= { x25Entry 18 }

uxx25-numOfrnrxsent  OBJECT-TYPE
       SYNTAX Counter
	   ACCESS read-only
	   STATUS mandatory
	   ::= { x25Entry 19 }

uxx25-numOfrnrxrece  OBJECT-TYPE
       SYNTAX Counter
	   ACCESS read-only
	   STATUS mandatory
	   ::= { x25Entry 20 }

uxx25-numOfresetsent  OBJECT-TYPE
       SYNTAX Counter
	   ACCESS read-only
	   STATUS mandatory
	   ::= { x25Entry 21 }

uxx25-numOfresetrece  OBJECT-TYPE
       SYNTAX Counter
	   ACCESS read-only
	   STATUS mandatory
	   ::= { x25Entry 22 }

uxx25-numOfrejxsent  OBJECT-TYPE
       SYNTAX Counter
	   ACCESS read-only
	   STATUS mandatory
	   ::= { x25Entry 23 }

uxx25-numOfrejxrece  OBJECT-TYPE
       SYNTAX Counter
	   ACCESS read-only
	   STATUS mandatory
	   ::= { x25Entry 24 }

uxx25-numOfdiagnsent  OBJECT-TYPE
       SYNTAX Counter
	   ACCESS read-only
	   STATUS mandatory
	   ::= { x25Entry 25 }

uxx25-numOfdiagnrece  OBJECT-TYPE
       SYNTAX Counter
	   ACCESS read-only
	   STATUS mandatory
	   ::= { x25Entry 26 }

uxx25-numOfregistsent  OBJECT-TYPE
       SYNTAX Counter
	   ACCESS read-only
	   STATUS mandatory
	   ::= { x25Entry 27 }

uxx25-numOfregistrece  OBJECT-TYPE
       SYNTAX Counter
	   ACCESS read-only
	   STATUS mandatory
	   ::= { x25Entry 28 }

uxx25-numOfrestretries  OBJECT-TYPE
       SYNTAX Counter
	   ACCESS read-only
	   STATUS mandatory
	   ::= { x25Entry 29 }

uxx25-numOfrestunsucfull  OBJECT-TYPE
       SYNTAX Counter
	   ACCESS read-only
	   STATUS mandatory
	   ::= { x25Entry 30 }

uxx25-numOfsyntaxerrors  OBJECT-TYPE
       SYNTAX Counter
	   ACCESS read-only
	   STATUS mandatory
	   ::= { x25Entry 31 }

uxx25-numOflogicalerrors  OBJECT-TYPE
       SYNTAX Counter
	   ACCESS read-only
	   STATUS mandatory
	   ::= { x25Entry 32 }

uxx25-numOfcallunsucfull  OBJECT-TYPE
       SYNTAX Counter
	   ACCESS read-only
	   STATUS mandatory
	   ::= { x25Entry 33 }

uxx25-numOfclearretries  OBJECT-TYPE
       SYNTAX Counter
	   ACCESS read-only
	   STATUS mandatory
	   ::= { x25Entry 34 }

uxx25-numOfclearunsucfull  OBJECT-TYPE
       SYNTAX Counter
	   ACCESS read-only
	   STATUS mandatory
	   ::= { x25Entry 35 }

uxx25-numOfinterunsucfull  OBJECT-TYPE
       SYNTAX Counter
	   ACCESS read-only
	   STATUS mandatory
	   ::= { x25Entry 36 }

uxx25-numOfresetretries  OBJECT-TYPE
       SYNTAX Counter
	   ACCESS read-only
	   STATUS mandatory
	   ::= { x25Entry 37 }

uxx25-numOfresetunsucfull  OBJECT-TYPE
       SYNTAX Counter
	   ACCESS read-only
	   STATUS mandatory
	   ::= { x25Entry 38 }

uxx25-numOfdataretrsucfull  OBJECT-TYPE
       SYNTAX Counter
	   ACCESS read-only
	   STATUS mandatory
	   ::= { x25Entry 39 }

uxx25-numOfdataretrunsucfull  OBJECT-TYPE
       SYNTAX Counter
	   ACCESS read-only
	   STATUS mandatory
	   ::= { x25Entry 40 }

uxx25-numOfrejretries  OBJECT-TYPE
       SYNTAX Counter
	   ACCESS read-only
	   STATUS mandatory
	   ::= { x25Entry 41 }

uxx25-numOfrejunsucfull  OBJECT-TYPE
       SYNTAX Counter
	   ACCESS read-only
	   STATUS mandatory
	   ::= { x25Entry 42 }

uxx25-numOfInformat  OBJECT-TYPE
       SYNTAX Counter
	   ACCESS read-only
	   STATUS mandatory
	   ::= { x25Entry 43 }

 --...................................................................
 --...................................................................

tp02Table    OBJECT-TYPE
       SYNTAX SEQUENCE OF Tp02Entry
	   ACCESS not-accessible
	   STATUS mandatory
	   ::= { tp02 1 }

tp02Entry    OBJECT-TYPE
       SYNTAX Tp02Entry  
	   ACCESS not-accessible
	   STATUS mandatory
	   INDEX  { uxtp02-tp02SysName,
		    uxtp02-tp02InstName,
		    uxtp02-tp02SubAddr }
	   ::= { tp02Table 1 }

Tp02Entry ::= SEQUENCE {
                       uxtp02-tp02SysName DisplayString,
                       uxtp02-tp02InstName DisplayString,
                       uxtp02-tp02SubAddr DisplayString,
                       uxtp02-numOfzeroingtime  Counter,
                       uxtp02-numOfnumberTPDUSent Counter,
                       uxtp02-numOfnumberTPDUReceived Counter,
                       uxtp02-numOftDataSent Counter,
                       uxtp02-numOftExpeditedDataSent Counter,
                       uxtp02-numOftDataReceived Counter,
                       uxtp02-numOftExpeditedDataReceived Counter,
                       uxtp02-numOfopenConnection Counter,
                       uxtp02-numOfctTPDUSuccessfullIncoming Counter,
                       uxtp02-numOfctTPDUSuccessfullOutgoing Counter,
                       uxtp02-numOfctTPDUUnSuccessfullIncoming Counter,
                       uxtp02-numOfctTPDUUnSuccessfullOutgoing Counter,
                       uxtp02-numOfctTPDUCongestion Counter,
                       uxtp02-numOfctTPDUConfProtErrorDetected Counter,
                       uxtp02-numOfctTPDURefusedConfProtError Counter,
                       uxtp02-numOfdetectedTPDUProtocolError Counter,
                       uxtp02-numOfrefusedTPDUProtocolError Counter
					   }
					   
uxtp02-tp02SysName OBJECT-TYPE
       SYNTAX DisplayString (SIZE(0..16))
	   ACCESS read-only
	   STATUS mandatory
	   ::= { tp02Entry 1 }

uxtp02-tp02InstName OBJECT-TYPE
       SYNTAX DisplayString (SIZE(0..14))
	   ACCESS read-only
	   STATUS mandatory
	   ::= { tp02Entry 2 }

uxtp02-tp02SubAddr  OBJECT-TYPE
       SYNTAX DisplayString (SIZE(0..16))
	   ACCESS read-only
	   STATUS mandatory
	   ::= { tp02Entry 3 }

uxtp02-numOfzeroingtime  OBJECT-TYPE
       SYNTAX Counter
	   ACCESS read-only
	   STATUS mandatory
	   ::= { tp02Entry 4 }

uxtp02-numOfnumberTPDUSent OBJECT-TYPE
       SYNTAX Counter
	   ACCESS read-only
	   STATUS mandatory
	   ::= { tp02Entry 5 }

uxtp02-numOfnumberTPDUReceived OBJECT-TYPE
       SYNTAX Counter
	   ACCESS read-only
	   STATUS mandatory
	   ::= { tp02Entry 6 }

uxtp02-numOftDataSent OBJECT-TYPE
       SYNTAX Counter
	   ACCESS read-only
	   STATUS mandatory
	   ::= { tp02Entry 7 }

uxtp02-numOftExpeditedDataSent OBJECT-TYPE
       SYNTAX Counter
	   ACCESS read-only
	   STATUS mandatory
	   ::= { tp02Entry 8 }

uxtp02-numOftDataReceived OBJECT-TYPE
       SYNTAX Counter
	   ACCESS read-only
	   STATUS mandatory

	   ::= { tp02Entry 9 }

uxtp02-numOftExpeditedDataReceived OBJECT-TYPE
       SYNTAX Counter
	   ACCESS read-only
	   STATUS mandatory
	   ::= { tp02Entry 10 }

uxtp02-numOfopenConnection OBJECT-TYPE
       SYNTAX Counter
	   ACCESS read-only
	   STATUS mandatory
	   ::= { tp02Entry 11 }

uxtp02-numOfctTPDUSuccessfullIncoming OBJECT-TYPE
       SYNTAX Counter
	   ACCESS read-only
	   STATUS mandatory
	   ::= { tp02Entry 12 }

uxtp02-numOfctTPDUSuccessfullOutgoing OBJECT-TYPE
       SYNTAX Counter
	   ACCESS read-only
	   STATUS mandatory
	   ::= { tp02Entry 13 }

uxtp02-numOfctTPDUUnSuccessfullIncoming OBJECT-TYPE
       SYNTAX Counter
	   ACCESS read-only
	   STATUS mandatory
	   ::= { tp02Entry 14 }

uxtp02-numOfctTPDUUnSuccessfullOutgoing OBJECT-TYPE
       SYNTAX Counter
	   ACCESS read-only
	   STATUS mandatory
	   ::= { tp02Entry 15 }

uxtp02-numOfctTPDUCongestion OBJECT-TYPE
       SYNTAX Counter
	   ACCESS read-only
	   STATUS mandatory
	   ::= { tp02Entry 16 }

uxtp02-numOfctTPDUConfProtErrorDetected OBJECT-TYPE
       SYNTAX Counter
	   ACCESS read-only
	   STATUS mandatory
	   ::= { tp02Entry 17 }

uxtp02-numOfctTPDURefusedConfProtError OBJECT-TYPE
       SYNTAX Counter
	   ACCESS read-only
	   STATUS mandatory
	   ::= { tp02Entry 18 }

uxtp02-numOfdetectedTPDUProtocolError OBJECT-TYPE
       SYNTAX Counter
	   ACCESS read-only
	   STATUS mandatory
	   ::= { tp02Entry 19 }

uxtp02-numOfrefusedTPDUProtocolError OBJECT-TYPE
       SYNTAX Counter
	   ACCESS read-only
	   STATUS mandatory
	   ::= { tp02Entry 20 }

-- ELC DEFINITIONS ::= BEGIN
-- 
-- IMPORTS
--     enterprises,OBJECT-TYPE
-- 	    FROM RFC1155-SMI;
-- 
-- 
elc-MAC     OBJECT IDENTIFIER ::= { lsx-unix 18}
elc-ELC     OBJECT IDENTIFIER ::= { elc-MAC 0 }


elc-ELCTable    OBJECT-TYPE
       SYNTAX SEQUENCE OF ElcEntry
	   ACCESS not-accessible
	   STATUS mandatory
	   ::= { elc-ELC 1 }


elc-ELCEntry    OBJECT-TYPE
       SYNTAX ElcEntry  
	   ACCESS not-accessible
	   STATUS mandatory
      INDEX {elcSysName,
             elcInstName,
             elcSubAddr}
	   ::= { elc-ELCTable 1 }

ElcEntry ::= SEQUENCE {
                         elcSysName DisplayString,
                         elcInstName DisplayString,
                         elcSubAddr DisplayString,
			 elctxsuccess Counter,
			 elctxcollision Counter,
			 elcSQEtsterrors Counter,
			 elcrxsuccess Counter,
			 elcrxCRC Counter,
			 elcrxalignment Counter,
			 elcrxnobuffer Counter,
			 elcrxoverrun Counter,
			 elcrxshframe Counter,
			 elcrxcollision Counter,
			 elctxattempted Counter,
			 elctxlostCS Counter,
			 elctxlostCTS Counter,
			 elctxunderrun Counter,
			 elctxmaxcollision Counter,
			 elctxdeferred Counter,
			 elctxframexceeding Counter,
			 elctxbytesuccess Counter
					   }
					   
elcSysName OBJECT-TYPE
       SYNTAX DisplayString (SIZE(0..16))
	   ACCESS read-only
	   STATUS mandatory
	   ::= { elc-ELCEntry 1 }

elcInstName OBJECT-TYPE
       SYNTAX DisplayString (SIZE(0..14))
	   ACCESS read-only
	   STATUS mandatory
	   ::= { elc-ELCEntry 2 }

elcSubAddr  OBJECT-TYPE
       SYNTAX DisplayString (SIZE(0..16))
	   ACCESS read-only
	   STATUS mandatory
	   ::= { elc-ELCEntry 3 }

elctxsuccess 	OBJECT-TYPE
       SYNTAX Counter
	   ACCESS read-only
	   STATUS mandatory
	   ::= { elc-ELCEntry 4 }

elctxcollision 	OBJECT-TYPE
       SYNTAX Counter
	   ACCESS read-only
	   STATUS mandatory
	   ::= { elc-ELCEntry 5 }

elcSQEtsterrors 	OBJECT-TYPE
       SYNTAX Counter
	   ACCESS read-only
	   STATUS mandatory
	   ::= { elc-ELCEntry 6 }

elcrxsuccess 	OBJECT-TYPE
       SYNTAX Counter
	   ACCESS read-only
	   STATUS mandatory
	   ::= { elc-ELCEntry 7 }

elcrxCRC 	OBJECT-TYPE
       SYNTAX Counter
	   ACCESS read-only
	   STATUS mandatory
	   ::= { elc-ELCEntry 8 }

elcrxalignment 	OBJECT-TYPE
       SYNTAX Counter
	   ACCESS read-only
	   STATUS mandatory
	   ::= { elc-ELCEntry 9 }

elcrxnobuffer 	OBJECT-TYPE
       SYNTAX Counter
	   ACCESS read-only
	   STATUS mandatory
	   ::= { elc-ELCEntry 10 }

elcrxoverrun 	OBJECT-TYPE
       SYNTAX Counter
	   ACCESS read-only
	   STATUS mandatory
	   ::= { elc-ELCEntry 11 }

elcrxshframe	OBJECT-TYPE
       SYNTAX Counter
	   ACCESS read-only
	   STATUS mandatory
	   ::= { elc-ELCEntry 12 }

elcrxcollision 	OBJECT-TYPE
       SYNTAX Counter
	   ACCESS read-only
	   STATUS mandatory
	   ::= { elc-ELCEntry 13 }

elctxattempted 	OBJECT-TYPE
       SYNTAX Counter
	   ACCESS read-only
	   STATUS mandatory
	   ::= { elc-ELCEntry 14 }

elctxlostCS 	OBJECT-TYPE
       SYNTAX Counter
	   ACCESS read-only
	   STATUS mandatory
	   ::= { elc-ELCEntry 15 }

elctxlostCTS 	OBJECT-TYPE
       SYNTAX Counter
	   ACCESS read-only
	   STATUS mandatory
	   ::= { elc-ELCEntry 16 }

elctxunderrun 	OBJECT-TYPE
       SYNTAX Counter
	   ACCESS read-only
	   STATUS mandatory
	   ::= { elc-ELCEntry 17 }

elctxmaxcollision 	OBJECT-TYPE
       SYNTAX Counter
	   ACCESS read-only
	   STATUS mandatory
	   ::= { elc-ELCEntry 18 }

elctxdeferred 	OBJECT-TYPE
       SYNTAX Counter
	   ACCESS read-only
	   STATUS mandatory
	   ::= { elc-ELCEntry 19 }

elctxframexceeding 	OBJECT-TYPE
       SYNTAX Counter
	   ACCESS read-only
	   STATUS mandatory
	   ::= { elc-ELCEntry 20 }

elctxbytesuccess 	OBJECT-TYPE
       SYNTAX Counter
	   ACCESS read-only
	   STATUS mandatory
	   ::= { elc-ELCEntry 21 }
-- 
-- ETHE DEFINITIONS ::= BEGIN
-- 
-- IMPORTS
--     enterprises,OBJECT-TYPE
-- 	    FROM RFC1155-SMI;
-- 
-- 
ethe-MAC1    OBJECT IDENTIFIER ::= { lsx-unix 19}
ethe-ETH     OBJECT IDENTIFIER ::= { ethe-MAC1 0 }


ethe-ETHTable    OBJECT-TYPE
       SYNTAX SEQUENCE OF EthEntry
	   ACCESS not-accessible
	   STATUS mandatory
	   ::= { ethe-ETH 1 }


ethe-ETHEntry    OBJECT-TYPE
       SYNTAX EthEntry  
	   ACCESS not-accessible
	   STATUS mandatory
      INDEX {etheSysName,
             etheInstName,
             etheSubAddr}
	   ::= { ethe-ETHTable 1 }


EthEntry ::= SEQUENCE {
                         etheSysName DisplayString,
                         etheInstName DisplayString,
                         etheSubAddr DisplayString,
			 ethetxsuccess Counter,
			 ethetxcollision Counter,
			 etheSQEtsterrors Counter,
			 etherxsuccess Counter,
			 etherxCRC Counter,
			 etherxalignment Counter,
			 etherxnobuffer Counter,
			 etherxoverrun Counter,
			 etherxshframe Counter,
			 etherxcollision Counter,
			 ethetxattempted Counter,
			 ethetxlostCS Counter,
			 ethetxlostCTS Counter,
			 ethetxunderrun Counter,
			 ethetxmaxcollision Counter,
			 ethetxdeferred Counter,
			 ethetxframexceeding Counter,
			 ethetxbytesuccess Counter
					   }
					   
etheSysName OBJECT-TYPE
       SYNTAX DisplayString (SIZE(0..16))
	   ACCESS read-only
	   STATUS mandatory
	   ::= { ethe-ETHEntry 1 }

etheInstName OBJECT-TYPE
       SYNTAX DisplayString (SIZE(0..14))
	   ACCESS read-only
	   STATUS mandatory
	   ::= { ethe-ETHEntry 2 }

etheSubAddr  OBJECT-TYPE
       SYNTAX DisplayString (SIZE(0..16))
	   ACCESS read-only
	   STATUS mandatory
	   ::= { ethe-ETHEntry 3 }

ethetxsuccess 	OBJECT-TYPE
       SYNTAX Counter
	   ACCESS read-only
	   STATUS mandatory
	   ::= { ethe-ETHEntry 4 }

ethetxcollision 	OBJECT-TYPE
       SYNTAX Counter
	   ACCESS read-only
	   STATUS mandatory
	   ::= { ethe-ETHEntry 5 }

etheSQEtsterrors 	OBJECT-TYPE
       SYNTAX Counter
	   ACCESS read-only
	   STATUS mandatory
	   ::= { ethe-ETHEntry 6 }

etherxsuccess 	OBJECT-TYPE
       SYNTAX Counter
	   ACCESS read-only
	   STATUS mandatory
	   ::= { ethe-ETHEntry 7 }

etherxCRC 		OBJECT-TYPE
       SYNTAX Counter
	   ACCESS read-only
	   STATUS mandatory
	   ::= { ethe-ETHEntry 8 }

etherxalignment 	OBJECT-TYPE
       SYNTAX Counter
	   ACCESS read-only
	   STATUS mandatory
	   ::= { ethe-ETHEntry 9 }

etherxnobuffer 	OBJECT-TYPE
       SYNTAX Counter
	   ACCESS read-only
	   STATUS mandatory
	   ::= { ethe-ETHEntry 10 }

etherxoverrun 	OBJECT-TYPE
       SYNTAX Counter
	   ACCESS read-only
	   STATUS mandatory
	   ::= { ethe-ETHEntry 11 }

etherxshframe 	OBJECT-TYPE
       SYNTAX Counter
	   ACCESS read-only
	   STATUS mandatory
	   ::= { ethe-ETHEntry 12 }

etherxcollision	OBJECT-TYPE
       SYNTAX Counter
	   ACCESS read-only
	   STATUS mandatory
	   ::= { ethe-ETHEntry 13 }

ethetxattempted 	OBJECT-TYPE
       SYNTAX Counter
	   ACCESS read-only
	   STATUS mandatory
	   ::= { ethe-ETHEntry 14 }

ethetxlostCS 	OBJECT-TYPE
       SYNTAX Counter
	   ACCESS read-only
	   STATUS mandatory
	   ::= { ethe-ETHEntry 15 }

ethetxlostCTS 	OBJECT-TYPE
       SYNTAX Counter
	   ACCESS read-only
	   STATUS mandatory
	   ::= { ethe-ETHEntry 16 }

ethetxunderrun 	OBJECT-TYPE
       SYNTAX Counter
	   ACCESS read-only
	   STATUS mandatory
	   ::= { ethe-ETHEntry 17 }

ethetxmaxcollision 	OBJECT-TYPE
       SYNTAX Counter
	   ACCESS read-only
	   STATUS mandatory
	   ::= { ethe-ETHEntry 18 }

ethetxdeferred 	OBJECT-TYPE
       SYNTAX Counter
	   ACCESS read-only
	   STATUS mandatory
	   ::= { ethe-ETHEntry 19 }

ethetxframexceeding 	OBJECT-TYPE
       SYNTAX Counter
	   ACCESS read-only
	   STATUS mandatory
	   ::= { ethe-ETHEntry 20 }

ethetxbytesuccess 	OBJECT-TYPE
       SYNTAX Counter
	   ACCESS read-only
	   STATUS mandatory
	   ::= { ethe-ETHEntry 21 }
-- NETB DEFINITIONS ::= BEGIN
-- 
-- IMPORTS
--     enterprises,OBJECT-TYPE
-- 	    FROM RFC1155-SMI;
-- 
-- 
netb-NB     OBJECT IDENTIFIER ::= { lsx-unix 17}
netb-NBEUI  OBJECT IDENTIFIER ::= { netb-NB 0 }


netb-NBEUITable    OBJECT-TYPE
       SYNTAX SEQUENCE OF NBeuiEntry
	   ACCESS not-accessible
	   STATUS mandatory
	   ::= { netb-NBEUI 1 }

netb-NBEUIEntry    OBJECT-TYPE
       SYNTAX NBeuiEntry  
	   ACCESS not-accessible
	   STATUS mandatory
      INDEX {netbSysName,
             netbInstName,
             netbSubAddr}
	   ::= { netb-NBEUITable 1 }


NBeuiEntry ::= SEQUENCE {
                         netbSysName DisplayString,
                         netbInstName DisplayString,
                         netbSubAddr DisplayString,
                         netbreserved INTEGER,
                         netbreleaselevel INTEGER,
                         netbsoftwarelevel INTEGER,
                         netbadaptertype INTEGER,
                         netbparamstype INTEGER,
                         netbreportingperiod INTEGER,
                         netbrxFRMR Counter,
                         netbtxFRMR Counter,
                         netbrxIframeserr Counter,
                         netbtxaborted Counter,
                         netbtxsuccesspack Counter,
                         netbrxsuccesspack Counter,
                         netbtxIframeserr Counter,
                         netbrxnobuffer Counter,
                         netbT1expired Counter,
                         netbTiexpired Counter,
                         netbfreeNCB INTEGER,
                         netbconfiguredNCB INTEGER,
                         netbmaxNCB INTEGER,
                         netbtxnobuffer INTEGER,
                         netbmaxdatagram INTEGER,
                         netbpendingsession INTEGER,
                         netbconfiguredpending INTEGER,
                         netbmaxpending INTEGER,
                         netbmaxdatapacket INTEGER,
                         netbnumbernames INTEGER,
                         netbnumbersessions INTEGER,
                         netbDATAGRAMoutstanding INTEGER,
                         netbANYoustanding INTEGER
					   }

netbSysName OBJECT-TYPE
       SYNTAX DisplayString (SIZE(0..16))
	   ACCESS read-only
	   STATUS mandatory
	   ::= { netb-NBEUIEntry 1 }

netbInstName OBJECT-TYPE
       SYNTAX DisplayString (SIZE(0..14))
	   ACCESS read-only
	   STATUS mandatory
	   ::= { netb-NBEUIEntry 2 }

netbSubAddr  OBJECT-TYPE
       SYNTAX DisplayString (SIZE(0..16))
	   ACCESS read-only
	   STATUS mandatory
	   ::= { netb-NBEUIEntry 3 }

netbreserved OBJECT-TYPE
       SYNTAX INTEGER
	   ACCESS read-only
	   STATUS mandatory
	   ::= { netb-NBEUIEntry 4 }

netbreleaselevel OBJECT-TYPE
       SYNTAX INTEGER
	   ACCESS read-only
	   STATUS mandatory
	   ::= { netb-NBEUIEntry 5 }

netbsoftwarelevel OBJECT-TYPE
       SYNTAX INTEGER
	   ACCESS read-only
	   STATUS mandatory
	   ::= { netb-NBEUIEntry 6 }

netbadaptertype OBJECT-TYPE
       SYNTAX INTEGER
	   ACCESS read-only
	   STATUS mandatory
	   ::= { netb-NBEUIEntry 7 }

netbparamstype OBJECT-TYPE
       SYNTAX INTEGER
	   ACCESS read-only
	   STATUS mandatory
	   ::= { netb-NBEUIEntry 8 }

netbreportingperiod OBJECT-TYPE
       SYNTAX INTEGER
	   ACCESS read-only
	   STATUS mandatory
	   ::= { netb-NBEUIEntry 9 }

netbrxFRMR OBJECT-TYPE
       SYNTAX Counter
	   ACCESS read-only
	   STATUS mandatory
	   ::= { netb-NBEUIEntry 10 }

netbtxFRMR OBJECT-TYPE
       SYNTAX Counter
	   ACCESS read-only
	   STATUS mandatory
	   ::= { netb-NBEUIEntry 11 }

netbrxIframeserr OBJECT-TYPE
       SYNTAX Counter
	   ACCESS read-only
	   STATUS mandatory
	   ::= { netb-NBEUIEntry 12 }

netbtxaborted OBJECT-TYPE
       SYNTAX Counter
	   ACCESS read-only
	   STATUS mandatory
	   ::= { netb-NBEUIEntry 13 }

netbtxsuccesspack OBJECT-TYPE
       SYNTAX Counter
	   ACCESS read-only
	   STATUS mandatory
	   ::= { netb-NBEUIEntry 14 }

netbrxsuccesspack OBJECT-TYPE
       SYNTAX Counter
	   ACCESS read-only
	   STATUS mandatory
	   ::= { netb-NBEUIEntry 15 }

netbtxIframeserr OBJECT-TYPE
       SYNTAX Counter
	   ACCESS read-only
	   STATUS mandatory
	   ::= { netb-NBEUIEntry 16 }

netbrxnobuffer OBJECT-TYPE
       SYNTAX Counter
	   ACCESS read-only
	   STATUS mandatory
	   ::= { netb-NBEUIEntry 17 }

netbT1expired OBJECT-TYPE
       SYNTAX Counter
	   ACCESS read-only
	   STATUS mandatory
	   ::= { netb-NBEUIEntry 18 }

netbTiexpired OBJECT-TYPE
       SYNTAX Counter
	   ACCESS read-only
	   STATUS mandatory
	   ::= { netb-NBEUIEntry 19 }

netbfreeNCB OBJECT-TYPE
       SYNTAX INTEGER
	   ACCESS read-only
	   STATUS mandatory
	   ::= { netb-NBEUIEntry 20 }

netbconfiguredNCB OBJECT-TYPE
       SYNTAX INTEGER
	   ACCESS read-only
	   STATUS mandatory
	   ::= { netb-NBEUIEntry 21 }

netbmaxNCB OBJECT-TYPE
       SYNTAX INTEGER
	   ACCESS read-only
	   STATUS mandatory
	   ::= { netb-NBEUIEntry 22 }

netbtxnobuffer OBJECT-TYPE
       SYNTAX INTEGER
	   ACCESS read-only
	   STATUS mandatory
	   ::= { netb-NBEUIEntry 23 }

netbmaxdatagram OBJECT-TYPE
       SYNTAX INTEGER
	   ACCESS read-only
	   STATUS mandatory
	   ::= { netb-NBEUIEntry 24 }

netbpendingsession OBJECT-TYPE
       SYNTAX INTEGER
	   ACCESS read-only
	   STATUS mandatory
	   ::= { netb-NBEUIEntry 25 }

netbconfiguredpending OBJECT-TYPE
       SYNTAX INTEGER
	   ACCESS read-only
	   STATUS mandatory
	   ::= { netb-NBEUIEntry 26 }

netbmaxpending OBJECT-TYPE
       SYNTAX INTEGER
	   ACCESS read-only
	   STATUS mandatory
	   ::= { netb-NBEUIEntry 27 }

netbmaxdatapacket OBJECT-TYPE
       SYNTAX INTEGER
	   ACCESS read-only
	   STATUS mandatory
	   ::= { netb-NBEUIEntry 28 }

netbnumbernames OBJECT-TYPE
       SYNTAX INTEGER
	   ACCESS read-only
	   STATUS mandatory
	   ::= { netb-NBEUIEntry 29 }

netbnumbersessions OBJECT-TYPE
       SYNTAX INTEGER
	   ACCESS read-only
	   STATUS mandatory
	   ::= { netb-NBEUIEntry 30 }

netbDATAGRAMoutstanding OBJECT-TYPE
       SYNTAX INTEGER
	   ACCESS read-only
	   STATUS mandatory
	   ::= { netb-NBEUIEntry 31 }

netbANYoustanding OBJECT-TYPE
       SYNTAX INTEGER
	   ACCESS read-only
	   STATUS mandatory
	   ::= { netb-NBEUIEntry 32 }

-- ONETWARE DEFINITIONS ::= BEGIN
-- 
-- IMPORTS
--     enterprises,OBJECT-TYPE
-- 	    FROM RFC1155-SMI;
-- 
-- 
onetware-NW     OBJECT IDENTIFIER ::= { lsx-unix 53}
onetware-SRVNW  OBJECT IDENTIFIER ::= { onetware-NW 1 }


onetware-SRVNWTable    OBJECT-TYPE
       SYNTAX SEQUENCE OF SrvNWEntry
	   ACCESS not-accessible
	   STATUS mandatory
	   ::= { onetware-SRVNW 1 }

onetware-SRVNWEntry    OBJECT-TYPE
       SYNTAX SrvNWEntry  
	   ACCESS not-accessible
	   STATUS mandatory
      INDEX {onetwareSysName,
             onetwareInstName,
             onetwareSubAddr}
	   ::= { onetware-SRVNWTable 1 }


SrvNWEntry ::= SEQUENCE {
                         onetwareSysName DisplayString,
                         onetwareInstName DisplayString,
                         onetwareSubAddr DisplayString,
                         onetwareMaxClientConnSupported Counter,
                         onetwareClientConnInUse Counter,
                         onetwarePeakClientConnUsed Counter,
                         onetwareMaxVolumes Counter,
                         onetwareNWProcs Counter,
                         onetwareTotalPackets INTEGER,
                         onetwareCreateConnectionRequests INTEGER,
                         onetwareCreateFileRequests INTEGER,
                         onetwareOpenRequests INTEGER,
                         onetwareReadRequests INTEGER,
                         onetwareWriteRequests INTEGER,
                         onetwareNumOpenFiles Counter,
                         onetwareMaxSimultaneousOpens Counter,
                         onetwareLostPacketResends INTEGER,
                         onetwareCacheHits INTEGER,
                         onetwareCacheMisses INTEGER,
                         onetwarePrintRequests INTEGER,
                         onetwareMessageRequests INTEGER,
                         onetwareDirectoryRequests INTEGER,
                         onetwareBinderyAndMiscRequests INTEGER,
                         onetwareUnknownRequests INTEGER,
                         onetwareSharedMemorySize Counter,
                         onetwareCurrentSharedMemoryUsage Counter,
                         onetwareMaxSharedMemoryUsed Counter,
                         onetwareLogicalLockRequests INTEGER,
                         onetwareNumLogicalLocks Counter,
                         onetwareMaxSimultaneousLogLocks Counter,
                         onetwareFileLockRequests INTEGER,
                         onetwareNumFileLocks Counter,
                         onetwareMaxSimultaneousFileLocks Counter,
                         onetwarePhysLockRequests INTEGER,
                         onetwareNumPhysLocks Counter,
                         onetwareMaxSimultaneousPhysLocks Counter,
                         onetwareSemaphoreRequests INTEGER,
                         onetwareNumSemaphores Counter,
                         onetwareMaxSimultaneousSemaphores Counter
					   }
					   
onetwareSysName OBJECT-TYPE
       SYNTAX DisplayString (SIZE(0..16))
	   ACCESS read-only
	   STATUS mandatory
	   ::= { onetware-SRVNWEntry 1 }

onetwareInstName OBJECT-TYPE
       SYNTAX DisplayString (SIZE(0..14))
	   ACCESS read-only
	   STATUS mandatory
	   ::= { onetware-SRVNWEntry 2 }

onetwareSubAddr  OBJECT-TYPE
       SYNTAX DisplayString (SIZE(0..16))
	   ACCESS read-only
	   STATUS mandatory
	   ::= { onetware-SRVNWEntry 3 }

onetwareMaxClientConnSupported OBJECT-TYPE
       SYNTAX Counter
	   ACCESS read-only
	   STATUS mandatory
	   ::= { onetware-SRVNWEntry 4 }

onetwareClientConnInUse OBJECT-TYPE
       SYNTAX Counter
	   ACCESS read-only
	   STATUS mandatory
	   ::= { onetware-SRVNWEntry 5 }

onetwarePeakClientConnUsed OBJECT-TYPE
       SYNTAX Counter
	   ACCESS read-only
	   STATUS mandatory
	   ::= { onetware-SRVNWEntry 6 }

onetwareMaxVolumes OBJECT-TYPE
       SYNTAX Counter
	   ACCESS read-only
	   STATUS mandatory
	   ::= { onetware-SRVNWEntry 7 }

onetwareNWProcs OBJECT-TYPE
       SYNTAX Counter
	   ACCESS read-only
	   STATUS mandatory
	   ::= { onetware-SRVNWEntry 8 }

onetwareTotalPackets OBJECT-TYPE
       SYNTAX INTEGER
	   ACCESS read-write
	   STATUS mandatory
	   ::= { onetware-SRVNWEntry 9 }

onetwareCreateConnectionRequests OBJECT-TYPE
       SYNTAX INTEGER
	   ACCESS read-write
	   STATUS mandatory
	   ::= { onetware-SRVNWEntry 10 }

onetwareCreateFileRequests OBJECT-TYPE
       SYNTAX INTEGER
	   ACCESS read-write
	   STATUS mandatory
	   ::= { onetware-SRVNWEntry 11 }

onetwareOpenRequests OBJECT-TYPE
       SYNTAX INTEGER
	   ACCESS read-write
	   STATUS mandatory
	   ::= { onetware-SRVNWEntry 12 }

onetwareReadRequests OBJECT-TYPE
       SYNTAX INTEGER
	   ACCESS read-write
	   STATUS mandatory
	   ::= { onetware-SRVNWEntry 13 }

onetwareWriteRequests OBJECT-TYPE
       SYNTAX INTEGER
	   ACCESS read-write
	   STATUS mandatory
	   ::= { onetware-SRVNWEntry 14 }

onetwareNumOpenFiles OBJECT-TYPE
       SYNTAX Counter
	   ACCESS read-only
	   STATUS mandatory
	   ::= { onetware-SRVNWEntry 15 }

onetwareMaxSimultaneousOpens OBJECT-TYPE
       SYNTAX Counter
	   ACCESS read-only
	   STATUS mandatory
	   ::= { onetware-SRVNWEntry 16 }

onetwareLostPacketResends OBJECT-TYPE
       SYNTAX INTEGER
	   ACCESS read-write
	   STATUS mandatory
	   ::= { onetware-SRVNWEntry 17 }

onetwareCacheHits OBJECT-TYPE
       SYNTAX INTEGER
	   ACCESS read-write
	   STATUS mandatory
	   ::= { onetware-SRVNWEntry 18 }

onetwareCacheMisses OBJECT-TYPE
       SYNTAX INTEGER
	   ACCESS read-write
	   STATUS mandatory
	   ::= { onetware-SRVNWEntry 19 }

onetwarePrintRequests OBJECT-TYPE
       SYNTAX INTEGER
	   ACCESS read-write
	   STATUS mandatory
	   ::= { onetware-SRVNWEntry 20 }

onetwareMessageRequests OBJECT-TYPE
       SYNTAX INTEGER
	   ACCESS read-write
	   STATUS mandatory
	   ::= { onetware-SRVNWEntry 21 }

onetwareDirectoryRequests OBJECT-TYPE
       SYNTAX INTEGER
	   ACCESS read-write
	   STATUS mandatory
	   ::= { onetware-SRVNWEntry 22 }

onetwareBinderyAndMiscRequests OBJECT-TYPE
       SYNTAX INTEGER
	   ACCESS read-write
	   STATUS mandatory
	   ::= { onetware-SRVNWEntry 23 }

onetwareUnknownRequests OBJECT-TYPE
       SYNTAX INTEGER
	   ACCESS read-write
	   STATUS mandatory
	   ::= { onetware-SRVNWEntry 24 }

onetwareSharedMemorySize OBJECT-TYPE
       SYNTAX Counter
	   ACCESS read-only
	   STATUS mandatory
	   ::= { onetware-SRVNWEntry 25 }

onetwareCurrentSharedMemoryUsage OBJECT-TYPE
       SYNTAX Counter
	   ACCESS read-only
	   STATUS mandatory
	   ::= { onetware-SRVNWEntry 26 }

onetwareMaxSharedMemoryUsed OBJECT-TYPE
       SYNTAX Counter
	   ACCESS read-only
	   STATUS mandatory
	   ::= { onetware-SRVNWEntry 27 }

onetwareLogicalLockRequests OBJECT-TYPE
       SYNTAX INTEGER
	   ACCESS read-write
	   STATUS mandatory
	   ::= { onetware-SRVNWEntry 28 }

onetwareNumLogicalLocks OBJECT-TYPE
       SYNTAX Counter
	   ACCESS read-only
	   STATUS mandatory
	   ::= { onetware-SRVNWEntry 29 }

onetwareMaxSimultaneousLogLocks OBJECT-TYPE
       SYNTAX Counter
	   ACCESS read-only
	   STATUS mandatory
	   ::= { onetware-SRVNWEntry 30 }

onetwareFileLockRequests OBJECT-TYPE
       SYNTAX INTEGER
	   ACCESS read-write
	   STATUS mandatory
	   ::= { onetware-SRVNWEntry 31 }

onetwareNumFileLocks OBJECT-TYPE
       SYNTAX Counter
	   ACCESS read-only
	   STATUS mandatory
	   ::= { onetware-SRVNWEntry 32 }

onetwareMaxSimultaneousFileLocks OBJECT-TYPE
       SYNTAX Counter
	   ACCESS read-only
	   STATUS mandatory
	   ::= { onetware-SRVNWEntry 33 }

onetwarePhysLockRequests OBJECT-TYPE
       SYNTAX INTEGER
	   ACCESS read-write
	   STATUS mandatory
	   ::= { onetware-SRVNWEntry 34 }

onetwareNumPhysLocks OBJECT-TYPE
       SYNTAX Counter
	   ACCESS read-only
	   STATUS mandatory
	   ::= { onetware-SRVNWEntry 35 }

onetwareMaxSimultaneousPhysLocks OBJECT-TYPE
       SYNTAX Counter
	   ACCESS read-only
	   STATUS mandatory
	   ::= { onetware-SRVNWEntry 36 }

onetwareSemaphoreRequests OBJECT-TYPE
       SYNTAX INTEGER
	   ACCESS read-write
	   STATUS mandatory
	   ::= { onetware-SRVNWEntry 37 }

onetwareNumSemaphores OBJECT-TYPE
       SYNTAX Counter
	   ACCESS read-only
	   STATUS mandatory
	   ::= { onetware-SRVNWEntry 38 }

onetwareMaxSimultaneousSemaphores OBJECT-TYPE
       SYNTAX Counter
	   ACCESS read-only
	   STATUS mandatory
	   ::= { onetware-SRVNWEntry 39 }

-- 
-- TNETB DEFINITIONS ::= BEGIN
-- 
-- IMPORTS
--     enterprises,OBJECT-TYPE
-- 	    FROM RFC1155-SMI;
-- 
-- 
tnetb-TNB     OBJECT IDENTIFIER ::= { lsx-unix 16}
tnetb-NETB    OBJECT IDENTIFIER ::= { tnetb-TNB 0 }

tnetb-NETBTable    OBJECT-TYPE
       SYNTAX SEQUENCE OF TNetbEntry
	   ACCESS not-accessible
	   STATUS mandatory
	   ::= { tnetb-NETB 1 }

tnetb-NETBEntry    OBJECT-TYPE
       SYNTAX TNetbEntry  
	   ACCESS not-accessible
	   STATUS mandatory
      INDEX {tnetb-NETBSysName,
             tnetb-NETBInstName,
             tnetb-NETBSubAddr}
	   ::= { tnetb-NETBTable 1 }


TNetbEntry ::= SEQUENCE {
                         tnetb-NETBSysName DisplayString,
                         tnetb-NETBInstName DisplayString,
                         tnetb-NETBSubAddr DisplayString,
                         tnetb-NETBtxPDU Counter,
                         tnetb-NETBrxPDU Counter,
                         tnetb-NETBsuccessregistr Counter,
                         tnetb-NETBunsuccessregistr Counter,
                         tnetb-NETBsuccessderegistr Counter,
                         tnetb-NETBunsuccessderegistr Counter,
                         tnetb-NETBresolutednames Counter,
                         tnetb-NETBunresolutednames Counter,
                         tnetb-NETBreserved Counter,
                         tnetb-NETBrxinvalidPDU Counter
					   }


tnetb-NETBSysName OBJECT-TYPE
       SYNTAX DisplayString (SIZE(0..16))
	   ACCESS read-only
	   STATUS mandatory
	   ::= { tnetb-NETBEntry 1 }

tnetb-NETBInstName OBJECT-TYPE
       SYNTAX DisplayString (SIZE(0..14))
	   ACCESS read-only
	   STATUS mandatory
	   ::= { tnetb-NETBEntry 2 }

tnetb-NETBSubAddr  OBJECT-TYPE
       SYNTAX DisplayString (SIZE(0..16))
	   ACCESS read-only
	   STATUS mandatory
	   ::= { tnetb-NETBEntry 3 }

tnetb-NETBtxPDU OBJECT-TYPE
       SYNTAX Counter
	   ACCESS read-only
	   STATUS mandatory
	   ::= { tnetb-NETBEntry 4 }

tnetb-NETBrxPDU OBJECT-TYPE
       SYNTAX Counter
	   ACCESS read-only
	   STATUS mandatory
	   ::= { tnetb-NETBEntry 5 }

tnetb-NETBsuccessregistr OBJECT-TYPE
       SYNTAX Counter
	   ACCESS read-only
	   STATUS mandatory
	   ::= { tnetb-NETBEntry 6 }

tnetb-NETBunsuccessregistr OBJECT-TYPE
       SYNTAX Counter
	   ACCESS read-only
	   STATUS mandatory
	   ::= { tnetb-NETBEntry 7 }

tnetb-NETBsuccessderegistr OBJECT-TYPE
       SYNTAX Counter
	   ACCESS read-only
	   STATUS mandatory
	   ::= { tnetb-NETBEntry 8 }

tnetb-NETBunsuccessderegistr OBJECT-TYPE
       SYNTAX Counter
	   ACCESS read-only
	   STATUS mandatory
	   ::= { tnetb-NETBEntry 9 }

tnetb-NETBresolutednames OBJECT-TYPE
       SYNTAX Counter
	   ACCESS read-only
	   STATUS mandatory
	   ::= { tnetb-NETBEntry 10 }

tnetb-NETBunresolutednames OBJECT-TYPE
       SYNTAX Counter
	   ACCESS read-only
	   STATUS mandatory
	   ::= { tnetb-NETBEntry 11 }

tnetb-NETBreserved OBJECT-TYPE
       SYNTAX Counter
	   ACCESS not-accessible
	   STATUS mandatory
	   ::= { tnetb-NETBEntry 12 }

tnetb-NETBrxinvalidPDU OBJECT-TYPE
       SYNTAX Counter
	   ACCESS read-only
	   STATUS mandatory
	   ::= { tnetb-NETBEntry 13 }


tnetb-TRSP    OBJECT IDENTIFIER ::= { tnetb-TNB 1 }

tnetb-TRSPTable    OBJECT-TYPE
       SYNTAX SEQUENCE OF TRspEntry
	   ACCESS not-accessible
	   STATUS mandatory
	   ::= { tnetb-TRSP 1 }

tnetb-TRSPEntry    OBJECT-TYPE
       SYNTAX TRspEntry  
	   ACCESS not-accessible
	   STATUS mandatory
      INDEX {tnetb-TRSPSysName,
             tnetb-TRSPInstName,
             tnetb-TRSPSubAddr}
	   ::= { tnetb-TRSPTable 1 }


TRspEntry ::= SEQUENCE {
                         tnetb-TRSPSysName DisplayString,
                         tnetb-TRSPInstName DisplayString,
                         tnetb-TRSPSubAddr DisplayString,
                         tnetb-TRSPreserved1 Counter,
                         tnetb-TRSPsuppconnection INTEGER,
                         tnetb-TRSPreserved2 Counter,
                         tnetb-TRSPreserved3 Counter,
                         tnetb-TRSPreserved4 Counter,
                         tnetb-TRSPreserved5 Counter,
                         tnetb-TRSPtxTPDU Counter,
                         tnetb-TRSPrxTPDU Counter,
                         tnetb-TRSPtxretranTPDU Counter,
                         tnetb-TRSPtxretranDATATPDU Counter,
                         tnetb-TRSPactiveconnection INTEGER,
                         tnetb-TRSPreserved6 Counter,
                         tnetb-TRSPsuccessinconnect Counter,
                         tnetb-TRSPsuccessoutconnect Counter,
                         tnetb-TRSPunsuccessinconnect Counter,
                         tnetb-TRSPunsuccessoutconnect Counter,
                         tnetb-TRSPconnectinactivity Counter,
                         tnetb-TRSPprotocolerror Counter,
                         tnetb-TRSPrxinvalidTPDU Counter,
                         tnetb-TRSPrxTSDU Counter,
                         tnetb-TRSPtxTSDU Counter,
                         tnetb-TRSPtxdatabyte Counter,
                         tnetb-TRSPrxdatabyte Counter,
                         tnetb-TRSPallocerror Counter,
                         tnetb-TRSPtxdatagramTPDU Counter,
                         tnetb-TRSPrxdatagrmTPDU Counter,
                         tnetb-TRSPoverrunTPDU Counter,
                         tnetb-TRSPopenerror Counter,
                         tnetb-TRSPnoendpoint Counter
					   }


tnetb-TRSPSysName OBJECT-TYPE
       SYNTAX DisplayString (SIZE(0..16))
	   ACCESS read-only
	   STATUS mandatory
	   ::= { tnetb-TRSPEntry 1 }

tnetb-TRSPInstName OBJECT-TYPE
       SYNTAX DisplayString (SIZE(0..14))
	   ACCESS read-only
	   STATUS mandatory
	   ::= { tnetb-TRSPEntry 2 }

tnetb-TRSPSubAddr  OBJECT-TYPE
       SYNTAX DisplayString (SIZE(0..16))
	   ACCESS read-only
	   STATUS mandatory
	   ::= { tnetb-TRSPEntry 3 }

tnetb-TRSPreserved1 OBJECT-TYPE
       SYNTAX Counter
	   ACCESS read-only
	   STATUS mandatory
	   ::= { tnetb-TRSPEntry 4 }

tnetb-TRSPsuppconnection OBJECT-TYPE
       SYNTAX INTEGER
	   ACCESS read-only
	   STATUS mandatory
	   ::= { tnetb-TRSPEntry 5 }

tnetb-TRSPreserved2 OBJECT-TYPE
       SYNTAX Counter
	   ACCESS read-only
	   STATUS mandatory
	   ::= { tnetb-TRSPEntry 6 }

tnetb-TRSPreserved3 OBJECT-TYPE
       SYNTAX Counter
	   ACCESS read-only
	   STATUS mandatory
	   ::= { tnetb-TRSPEntry 7 }

tnetb-TRSPreserved4 OBJECT-TYPE
       SYNTAX Counter
	   ACCESS read-only
	   STATUS mandatory
	   ::= { tnetb-TRSPEntry 8 }

tnetb-TRSPreserved5 OBJECT-TYPE
       SYNTAX Counter
	   ACCESS read-only
	   STATUS mandatory
	   ::= { tnetb-TRSPEntry 9 }

tnetb-TRSPtxTPDU OBJECT-TYPE
       SYNTAX Counter
	   ACCESS read-only
	   STATUS mandatory
	   ::= { tnetb-TRSPEntry 10 }

tnetb-TRSPrxTPDU OBJECT-TYPE
       SYNTAX Counter
	   ACCESS read-only
	   STATUS mandatory
	   ::= { tnetb-TRSPEntry 11 }

tnetb-TRSPtxretranTPDU OBJECT-TYPE
       SYNTAX Counter
	   ACCESS read-only
	   STATUS mandatory
	   ::= { tnetb-TRSPEntry 12 }

tnetb-TRSPtxretranDATATPDU OBJECT-TYPE
       SYNTAX Counter
	   ACCESS read-only
	   STATUS mandatory
	   ::= { tnetb-TRSPEntry 13 }

tnetb-TRSPactiveconnection OBJECT-TYPE
       SYNTAX INTEGER
	   ACCESS read-only
	   STATUS mandatory
	   ::= { tnetb-TRSPEntry 14 }

tnetb-TRSPreserved6 OBJECT-TYPE
       SYNTAX Counter
	   ACCESS read-only
	   STATUS mandatory
	   ::= { tnetb-TRSPEntry 15 }

tnetb-TRSPsuccessinconnect OBJECT-TYPE
       SYNTAX Counter
	   ACCESS read-only
	   STATUS mandatory
	   ::= { tnetb-TRSPEntry 16 }

tnetb-TRSPsuccessoutconnect OBJECT-TYPE
       SYNTAX Counter
	   ACCESS read-only
	   STATUS mandatory
	   ::= { tnetb-TRSPEntry 17 }

tnetb-TRSPunsuccessinconnect OBJECT-TYPE
       SYNTAX Counter
	   ACCESS read-only
	   STATUS mandatory
	   ::= { tnetb-TRSPEntry 18 }

tnetb-TRSPunsuccessoutconnect OBJECT-TYPE
       SYNTAX Counter
	   ACCESS read-only
	   STATUS mandatory
	   ::= { tnetb-TRSPEntry 19 }

tnetb-TRSPconnectinactivity OBJECT-TYPE
       SYNTAX Counter
	   ACCESS read-only
	   STATUS mandatory
	   ::= { tnetb-TRSPEntry 20 }

tnetb-TRSPprotocolerror OBJECT-TYPE
       SYNTAX Counter
	   ACCESS read-only
	   STATUS mandatory
	   ::= { tnetb-TRSPEntry 21 }

tnetb-TRSPrxinvalidTPDU OBJECT-TYPE
       SYNTAX Counter
	   ACCESS read-only
	   STATUS mandatory
	   ::= { tnetb-TRSPEntry 22 }

tnetb-TRSPrxTSDU OBJECT-TYPE
       SYNTAX Counter
	   ACCESS read-only
	   STATUS mandatory
	   ::= { tnetb-TRSPEntry 23 }

tnetb-TRSPtxTSDU OBJECT-TYPE
       SYNTAX Counter
	   ACCESS read-only
	   STATUS mandatory
	   ::= { tnetb-TRSPEntry 24 }

tnetb-TRSPtxdatabyte OBJECT-TYPE
       SYNTAX Counter
	   ACCESS read-only
	   STATUS mandatory
	   ::= { tnetb-TRSPEntry 25 }

tnetb-TRSPrxdatabyte OBJECT-TYPE
       SYNTAX Counter
	   ACCESS read-only
	   STATUS mandatory
	   ::= { tnetb-TRSPEntry 26 }

tnetb-TRSPallocerror OBJECT-TYPE
       SYNTAX Counter
	   ACCESS read-only
	   STATUS mandatory
	   ::= { tnetb-TRSPEntry 27 }

tnetb-TRSPtxdatagramTPDU OBJECT-TYPE
       SYNTAX Counter
	   ACCESS read-only
	   STATUS mandatory
	   ::= { tnetb-TRSPEntry 28 }

tnetb-TRSPrxdatagrmTPDU OBJECT-TYPE
       SYNTAX Counter
	   ACCESS read-only
	   STATUS mandatory
	   ::= { tnetb-TRSPEntry 29 }

tnetb-TRSPoverrunTPDU OBJECT-TYPE
       SYNTAX Counter
	   ACCESS read-only
	   STATUS mandatory
	   ::= { tnetb-TRSPEntry 30 }

tnetb-TRSPopenerror OBJECT-TYPE
       SYNTAX Counter
	   ACCESS read-only
	   STATUS mandatory
	   ::= { tnetb-TRSPEntry 31 }

tnetb-TRSPnoendpoint OBJECT-TYPE
       SYNTAX Counter
	   ACCESS read-only
	   STATUS mandatory
	   ::= { tnetb-TRSPEntry 32 }


tnetb-NTWK    OBJECT IDENTIFIER ::= { tnetb-TNB 2 }

tnetb-NTWKTable    OBJECT-TYPE
       SYNTAX SEQUENCE OF NtwkEntry
	   ACCESS not-accessible
	   STATUS mandatory
	   ::= { tnetb-NTWK 1 }

tnetb-NTWKEntry    OBJECT-TYPE
       SYNTAX NtwkEntry  
	   ACCESS not-accessible
	   STATUS mandatory
      INDEX {tnetb-NTWKSysName,
             tnetb-NTWKInstName,
             tnetb-NTWKSubAddr}
	   ::= { tnetb-NTWKTable 1 }


NtwkEntry ::= SEQUENCE {
                         tnetb-NTWKSysName DisplayString,
                         tnetb-NTWKInstName DisplayString,
                         tnetb-NTWKSubAddr DisplayString,
                         tnetb-NTWKresourceerror Counter,
                         tnetb-NTWKrxPDU Counter,
                         tnetb-NTWKtxPDU Counter,
                         tnetb-NTWKrxbyte Counter,
                         tnetb-NTWKtxbyte Counter,
                         tnetb-NTWKtxsegmented Counter,
                         tnetb-NTWKtxnetworkerror Counter,
                         tnetb-NTWKrxnetworkerror Counter,
                         tnetb-NTWKtxcongested Counter,
                         tnetb-NTWKrxreassembled Counter,
                         tnetb-NTWKreassemblytimeout Counter,
                         tnetb-NTWKtxforwarded Counter,
                         tnetb-NTWKPDUbadformat Counter,
                         tnetb-NTWKPDUdestinunreach Counter,
                         tnetb-NTWKPDUunsupportedoption Counter,
                         tnetb-NTWKlifetime Counter
					   }


tnetb-NTWKSysName OBJECT-TYPE
       SYNTAX DisplayString (SIZE(0..16))
	   ACCESS read-only
	   STATUS mandatory
	   ::= { tnetb-NTWKEntry 1 }

tnetb-NTWKInstName OBJECT-TYPE
       SYNTAX DisplayString (SIZE(0..14))
	   ACCESS read-only
	   STATUS mandatory
	   ::= { tnetb-NTWKEntry 2 }

tnetb-NTWKSubAddr  OBJECT-TYPE
       SYNTAX DisplayString (SIZE(0..16))
	   ACCESS read-only
	   STATUS mandatory
	   ::= { tnetb-NTWKEntry 3 }

tnetb-NTWKresourceerror OBJECT-TYPE
       SYNTAX Counter
	   ACCESS read-only
	   STATUS mandatory
	   ::= { tnetb-NTWKEntry 4 }

tnetb-NTWKrxPDU OBJECT-TYPE
       SYNTAX Counter
	   ACCESS read-only
	   STATUS mandatory
	   ::= { tnetb-NTWKEntry 5 }

tnetb-NTWKtxPDU OBJECT-TYPE
       SYNTAX Counter
	   ACCESS read-only
	   STATUS mandatory
	   ::= { tnetb-NTWKEntry 6 }

tnetb-NTWKrxbyte OBJECT-TYPE
       SYNTAX Counter
	   ACCESS read-only
	   STATUS mandatory
	   ::= { tnetb-NTWKEntry 7 }

tnetb-NTWKtxbyte OBJECT-TYPE
       SYNTAX Counter
	   ACCESS read-only
	   STATUS mandatory
	   ::= { tnetb-NTWKEntry 8 }

tnetb-NTWKtxsegmented OBJECT-TYPE
       SYNTAX Counter
	   ACCESS read-only
	   STATUS mandatory
	   ::= { tnetb-NTWKEntry 9 }

tnetb-NTWKtxnetworkerror OBJECT-TYPE
       SYNTAX Counter
	   ACCESS read-only
	   STATUS mandatory
	   ::= { tnetb-NTWKEntry 10 }

tnetb-NTWKrxnetworkerror OBJECT-TYPE
       SYNTAX Counter
	   ACCESS read-only
	   STATUS mandatory
	   ::= { tnetb-NTWKEntry 11 }

tnetb-NTWKtxcongested OBJECT-TYPE
       SYNTAX Counter
	   ACCESS read-only
	   STATUS mandatory
	   ::= { tnetb-NTWKEntry 12 }

tnetb-NTWKrxreassembled OBJECT-TYPE
       SYNTAX Counter
	   ACCESS read-only
	   STATUS mandatory
	   ::= { tnetb-NTWKEntry 13 }

tnetb-NTWKreassemblytimeout OBJECT-TYPE
       SYNTAX Counter
	   ACCESS read-only
	   STATUS mandatory
	   ::= { tnetb-NTWKEntry 14 }

tnetb-NTWKtxforwarded OBJECT-TYPE
       SYNTAX Counter
	   ACCESS read-only
	   STATUS mandatory
	   ::= { tnetb-NTWKEntry 15 }

tnetb-NTWKPDUbadformat OBJECT-TYPE
       SYNTAX Counter
	   ACCESS read-only
	   STATUS mandatory
	   ::= { tnetb-NTWKEntry 16 }

tnetb-NTWKPDUdestinunreach OBJECT-TYPE
       SYNTAX Counter
	   ACCESS read-only
	   STATUS mandatory
	   ::= { tnetb-NTWKEntry 17 }

tnetb-NTWKPDUunsupportedoption OBJECT-TYPE
       SYNTAX Counter
	   ACCESS read-only
	   STATUS mandatory
	   ::= { tnetb-NTWKEntry 18 }

tnetb-NTWKlifetime OBJECT-TYPE
       SYNTAX Counter
	   ACCESS read-only
	   STATUS mandatory
	   ::= { tnetb-NTWKEntry 19 }


tnetb-LLCN    OBJECT IDENTIFIER ::= { tnetb-TNB 3 }

tnetb-LLCNTable    OBJECT-TYPE
       SYNTAX SEQUENCE OF LlcnEntry
	   ACCESS not-accessible
	   STATUS mandatory
	   ::= { tnetb-LLCN 1 }

tnetb-LLCNEntry    OBJECT-TYPE
       SYNTAX LlcnEntry  
	   ACCESS not-accessible
	   STATUS mandatory
      INDEX {tnetb-LLCNSysName,
             tnetb-LLCNInstName,
             tnetb-LLCNSubAddr}
	   ::= { tnetb-LLCNTable 1 }


LlcnEntry ::= SEQUENCE {
			 tnetb-LLCNSysName DisplayString,
                         tnetb-LLCNInstName DisplayString,
                         tnetb-LLCNSubAddr DisplayString,
                         tnetb-LLCNtxUI5rame Counter,
                         tnetb-LLCNrxUIframe Counter,
                         tnetb-LLCNtxMACerror Counter,
                         tnetb-LLCNrxMACerror Counter,
                         tnetb-LLCNtxTESTframe Counter,
                         tnetb-LLCNrxTESTframe Counter,
                         tnetb-LLCNtxXIDframe Counter,
                         tnetb-LLCNrxXIDframe Counter,
                         tnetb-LLCNtxTESTresponse Counter,
                         tnetb-LLCNrxTESTresponse Counter,
                         tnetb-LLCNtxXIDresponse Counter,
                         tnetb-LLCNrxXIDresponse Counter
					   }


tnetb-LLCNSysName OBJECT-TYPE
       SYNTAX DisplayString (SIZE(0..16))
	   ACCESS read-only
	   STATUS mandatory
	   ::= { tnetb-LLCNEntry 1 }

tnetb-LLCNInstName OBJECT-TYPE
       SYNTAX DisplayString (SIZE(0..14))
	   ACCESS read-only
	   STATUS mandatory
	   ::= { tnetb-LLCNEntry 2 }

tnetb-LLCNSubAddr  OBJECT-TYPE
       SYNTAX DisplayString (SIZE(0..16))
	   ACCESS read-only
	   STATUS mandatory
	   ::= { tnetb-LLCNEntry 3 }

tnetb-LLCNtxUI5rame OBJECT-TYPE
       SYNTAX Counter
	   ACCESS read-only
	   STATUS mandatory
	   ::= { tnetb-LLCNEntry 4 }

tnetb-LLCNrxUIframe OBJECT-TYPE
       SYNTAX Counter
	   ACCESS read-only
	   STATUS mandatory
	   ::= { tnetb-LLCNEntry 5 }

tnetb-LLCNtxMACerror OBJECT-TYPE
       SYNTAX Counter
	   ACCESS read-only
	   STATUS mandatory
	   ::= { tnetb-LLCNEntry 6 }

tnetb-LLCNrxMACerror OBJECT-TYPE
       SYNTAX Counter
	   ACCESS read-only
	   STATUS mandatory
	   ::= { tnetb-LLCNEntry 7 }

tnetb-LLCNtxTESTframe OBJECT-TYPE
       SYNTAX Counter
	   ACCESS read-only
	   STATUS mandatory
	   ::= { tnetb-LLCNEntry 8 }

tnetb-LLCNrxTESTframe OBJECT-TYPE
       SYNTAX Counter
	   ACCESS read-only
	   STATUS mandatory
	   ::= { tnetb-LLCNEntry 9 }

tnetb-LLCNtxXIDframe OBJECT-TYPE
       SYNTAX Counter
	   ACCESS read-only
	   STATUS mandatory
	   ::= { tnetb-LLCNEntry 10 }

tnetb-LLCNrxXIDframe OBJECT-TYPE
       SYNTAX Counter
	   ACCESS read-only
	   STATUS mandatory
	   ::= { tnetb-LLCNEntry 11 }

tnetb-LLCNtxTESTresponse OBJECT-TYPE
       SYNTAX Counter
	   ACCESS read-only
	   STATUS mandatory
	   ::= { tnetb-LLCNEntry 12 }

tnetb-LLCNrxTESTresponse OBJECT-TYPE
       SYNTAX Counter
	   ACCESS read-only
	   STATUS mandatory
	   ::= { tnetb-LLCNEntry 13 }

tnetb-LLCNtxXIDresponse OBJECT-TYPE
       SYNTAX Counter
	   ACCESS read-only
	   STATUS mandatory
	   ::= { tnetb-LLCNEntry 14 }

tnetb-LLCNrxXIDresponse OBJECT-TYPE
       SYNTAX Counter
	   ACCESS read-only
	   STATUS mandatory
	   ::= { tnetb-LLCNEntry 15 }

END
