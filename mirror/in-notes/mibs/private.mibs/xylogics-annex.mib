--
--	Xylogics Annex Private Enterprise MIB
--
--  Copyright 1991, Xylogics, Inc.  ALL RIGHTS RESERVED.
--
--  ALL RIGHTS RESERVED. Licensed Material - Property of Xylogics, Inc.
--  This software is made available solely pursuant to the terms of a
--  software license agreement which governs its use.
--  Unauthorized duplication, distribution or sale are strictly prohibited.
--
--  This information is subject to change without notice, and should
--  not be construed as a commitment by Xylogics, Inc.  Xylogics, Inc.,
--  assumes no responsibility for any errors that may appear in this
--  document.
--
--  $Id: annex-mib.txt,v 1.17 92/09/18 13:17:48 barnes Exp $
--

-- overview

  ANNEX-MIB DEFINITIONS ::= BEGIN

  IMPORTS
		enterprises, NetworkAddress, IpAddress,
				Counter, Gauge, TimeTicks
			FROM RFC1155-SMI
		DisplayString, PhysAddress
			FROM RFC1213-MIB
		OBJECT-TYPE
			FROM RFC-1212;

  xylogics	OBJECT IDENTIFIER ::= { enterprises 15 } 

  prod		OBJECT IDENTIFIER ::= { xylogics 1 } 

  prodannex	OBJECT-TYPE
		SYNTAX DisplayString (SIZE (0..128))
		ACCESS read-only 
		STATUS mandatory
		DESCRIPTION
			"Product name."
		::= { prod 1 }

  annex		OBJECT IDENTIFIER ::= { xylogics 2 }

  hw		OBJECT IDENTIFIER ::= { annex 1 }
  sw		OBJECT IDENTIFIER ::= { annex 2 }
  ports		OBJECT IDENTIFIER ::= { annex 3 }
  parallelport	OBJECT IDENTIFIER ::= { annex 4 }
  annexconfig	OBJECT IDENTIFIER ::= { annex 5 }
  annexcmds	OBJECT IDENTIFIER ::= { annex 6 }

-- the hw group

  hwType	OBJECT-TYPE
		SYNTAX INTEGER {
			err(1),
			annexII(16),
			annex3(42),
			microannex(52),
			microels(55)
		}
		ACCESS read-only 
		STATUS mandatory
		DESCRIPTION
			"An identifier for the Annex hardware type."
		::= { hw 1 }

  hwRev		OBJECT-TYPE
		SYNTAX DisplayString (SIZE (0..128))
		ACCESS read-only 
		STATUS mandatory
		DESCRIPTION
			"The revision level of the hardware platform."
		::= { hw 2 }

  romRev	OBJECT-TYPE
		SYNTAX DisplayString (SIZE (0..128))
		ACCESS read-only 
		STATUS mandatory
		DESCRIPTION
			"The revision number of the ROM Monitor software."
		::= { hw 3 }

  serialNumber	OBJECT-TYPE
		SYNTAX INTEGER
		ACCESS read-only 
		STATUS mandatory
		DESCRIPTION
			"The serial number assigned to the unit."
		::= { hw 4 }

  memorySize	OBJECT-TYPE
		SYNTAX INTEGER
		ACCESS read-only 
		STATUS mandatory
		DESCRIPTION
			"The amount of memory present in the unit."
		::= { hw 5 }

-- the sw group

  swType	OBJECT-TYPE
		SYNTAX INTEGER {
			err(1),
			annexIImx(16),
			annexIIux(17),
			annex3ux(42),
			annex3mx(43),
			microannexux(52),
			microannexmx(53),
			microels(55)
		}
		ACCESS read-only 
		STATUS mandatory
		DESCRIPTION
			"The software version currently running on
			the Annex."
		::= { sw 1 }

  swRevMajor	OBJECT-TYPE
		SYNTAX INTEGER
		ACCESS read-only 
		STATUS mandatory
		DESCRIPTION
			"The major software release number."
		::= { sw 2 }

  swRevMinor	OBJECT-TYPE
		SYNTAX INTEGER
		ACCESS read-only 
		STATUS mandatory
		DESCRIPTION
			"The minor software release number."
		::= { sw 3 }

  swBuild	OBJECT-TYPE
		SYNTAX DisplayString (SIZE (0..128))
		ACCESS read-only 
		STATUS mandatory
		DESCRIPTION
			"The full name of the software build, including
			the software version, major and minor version
			numbers and the date and time of the build."
		::= { sw 4 }

  imageName	OBJECT-TYPE
		SYNTAX DisplayString (SIZE (0..100))
		ACCESS read-only 
		STATUS mandatory
		DESCRIPTION
			"The name of the most recently booted image."
		::= { sw 5 }

  bootHost	OBJECT-TYPE
		SYNTAX IpAddress
		ACCESS read-only 
		STATUS mandatory
		DESCRIPTION
			"The Internet address of the host from which
			the Annex booted."
		::= { sw 6 }

  defaultDomain	OBJECT-TYPE
		SYNTAX DisplayString (SIZE (0..128))
		ACCESS read-only 
		STATUS mandatory
		DESCRIPTION
			"The default domain name provided by the DNS
			nameserver."
		::= { sw 7 }

  currentDate	OBJECT-TYPE
		SYNTAX DisplayString (SIZE (0..64))
		ACCESS read-only 
		STATUS mandatory
		DESCRIPTION
			"The current date and time provided by the time
			server."
		::= { sw 8 }

  usableMemory	OBJECT-TYPE
		SYNTAX INTEGER
		ACCESS read-only 
		STATUS mandatory
		DESCRIPTION
			"The amount of available for data buffers and
			other structures after the Annex has booted."
		::= { sw 9 }

  freeMemory	OBJECT-TYPE
		SYNTAX Gauge
		ACCESS read-only 
		STATUS mandatory
		DESCRIPTION
			"The amount of currently available memory."
		::= { sw 10 }

  minFreeMemory	OBJECT-TYPE
		SYNTAX INTEGER
		ACCESS read-only 
		STATUS mandatory
		DESCRIPTION
			"The minimum amount of free memory since booting
			the Annex."
		::= { sw 11 }

  cpuUtilization	OBJECT-TYPE
		SYNTAX Gauge
		ACCESS read-only 
		STATUS mandatory
		DESCRIPTION
			"Percent of CPU time currently being used."
		::= { sw 12 }

  maxProcs	OBJECT-TYPE
		SYNTAX INTEGER
		ACCESS read-only 
		STATUS mandatory
		DESCRIPTION
			"The total number of process structures 
			allocated for use."
		::= { sw 13 }

  mostProcs	OBJECT-TYPE
		SYNTAX INTEGER
		ACCESS read-only 
		STATUS mandatory
		DESCRIPTION
			"The maximum number of active processes since
			the Annex was booted."
		::= { sw 14 }

  activeProcs	OBJECT-TYPE
		SYNTAX Gauge
		ACCESS read-only 
		STATUS mandatory
		DESCRIPTION
			"The number of currently active processes."
		::= { sw 15 }

  cpuIRescheds	OBJECT-TYPE
		SYNTAX Gauge
		ACCESS read-only 
		STATUS mandatory
		DESCRIPTION
			"The number of processes whose time slice has
			expired in the last minute."
		::= { sw 16 }

  cpuTRescheds	OBJECT-TYPE
		SYNTAX Counter
		ACCESS read-only 
		STATUS mandatory
		DESCRIPTION
			"The total number of processes whose time slice
			has expired since booting the Annex."
		::= { sw 17 }

  contextISwtchs	OBJECT-TYPE
		SYNTAX Gauge
		ACCESS read-only 
		STATUS mandatory
		DESCRIPTION
			"The number of context switches in the last 
			minute."
		::= { sw 18 }

  contextTSwtchs	OBJECT-TYPE
		SYNTAX Counter
		ACCESS read-only 
		STATUS mandatory
		DESCRIPTION
			"The total number of context switches since
			booting the Annex."
		::= { sw 19 }

  cpuIActivates	OBJECT-TYPE
		SYNTAX Gauge
		ACCESS read-only 
		STATUS mandatory
		DESCRIPTION
			"The number of processes that were activated
			in the last minute."
		::= { sw 20 }

  cpuTActivates	OBJECT-TYPE
		SYNTAX Counter
		ACCESS read-only 
		STATUS mandatory
		DESCRIPTION
			"The number of processes that were activated
			since booting the Annex."
		::= { sw 21 }
	
  maxCallouts	OBJECT-TYPE
		SYNTAX INTEGER
		ACCESS read-only 
		STATUS mandatory
		DESCRIPTION
			"The number of allocated Callout structures 
			for timed events in the Annex."
		::= { sw 22 }

  leastCallouts	OBJECT-TYPE
		SYNTAX INTEGER
		ACCESS read-only 
		STATUS mandatory
		DESCRIPTION
			"The minimum number of Callout structures 
			available since last booting the Annex."
		::= { sw 23 }

  freeCallouts	OBJECT-TYPE
		SYNTAX Gauge
		ACCESS read-only 
		STATUS mandatory
		DESCRIPTION
			"The current number of free Callout structures."
		::= { sw 24 }

-- the ports group

  totalPorts	OBJECT-TYPE
		SYNTAX INTEGER
		ACCESS read-only 
		STATUS mandatory
		DESCRIPTION
			"The number of serial ports on this Annex."
		::= { ports 1 }

  totalInChars	OBJECT-TYPE
		SYNTAX Counter
		ACCESS read-only 
		STATUS mandatory
		DESCRIPTION
			"The total number of characters received on all
			serial ports."
		::= { ports 2 }

  totalOutChars	OBJECT-TYPE
		SYNTAX Counter
		ACCESS read-only 
		STATUS mandatory
		DESCRIPTION
			"The total number of characters transmitted on
			all serial ports."
		::= { ports 3 }

  totalParityErrs	OBJECT-TYPE
		SYNTAX Counter
		ACCESS read-only 
		STATUS mandatory
		DESCRIPTION
			"The total number of parity errors detected
			on all serial ports."
		::= { ports 4 }

  totalOverrunErrs	OBJECT-TYPE
		SYNTAX Counter
		ACCESS read-only 
		STATUS mandatory
		DESCRIPTION
			"The total number of overruns detected on all
			serial ports."
		::= { ports 5 }

  totalFramingErrs	OBJECT-TYPE
		SYNTAX Counter
		ACCESS read-only 
		STATUS mandatory
		DESCRIPTION
			"The total number of framing errors detected
			on all serial ports."
		::= { ports 6 }

  portTable	OBJECT-TYPE
		SYNTAX SEQUENCE OF PortEntry
		ACCESS not-accessible
		STATUS mandatory
		DESCRIPTION
			"Table of port entries."
		::= { ports 7 }

  portEntry	OBJECT-TYPE
		SYNTAX PortEntry
		ACCESS not-accessible
		STATUS mandatory
		DESCRIPTION
			"The port's configuration parameters."
		INDEX  { anxpPortIndex }
		::= { portTable 1 }

  PortEntry	::= SEQUENCE {
	anxpPortIndex		INTEGER,
	anxpMode		INTEGER,
	anxpCtrlLines		INTEGER,
	anxpBidirModem		INTEGER,
	anxpAllowBcast		INTEGER,
	anxpBcastDirection	INTEGER,
	anxpInputStartChar	DisplayString,
	anxpInputStopChar	DisplayString,
	anxpOutputStartChar	DisplayString,
	anxpOutputStopChar	DisplayString,
	anxpIxanyFlowCtl	INTEGER,
	anxpLongBreak		INTEGER,
	anxpShortBreak		INTEGER,
	anxpForwardTimer	INTEGER,
	anxpForwardCount	INTEGER,
	anxpImask7Bits		INTEGER,
	anxpAttnChar		DisplayString,
	anxpInputBufSize	INTEGER,
	anxpInputIsActivity	INTEGER,
	anxpOutputIsActivity	INTEGER,
	anxpInactivityTimer	INTEGER,
	anxpResetIdleTimer	INTEGER,
	anxpCliInactivity	INTEGER,
	anxpCliSecurity		INTEGER,
	anxpConnectSecurity	INTEGER,
	anxpPortServerSecurity	INTEGER,
	anxpPortPassword	DisplayString,
	anxpUserName		DisplayString,
	anxpDedicatedAddr	IpAddress,
	anxpDedicatedPort	DisplayString,
	anxpPrompt		DisplayString,
	anxpTermVar		DisplayString,
	anxpNewLineTerm		INTEGER,
	anxpEcho		INTEGER,
	anxpMapToLower		INTEGER,
	anxpMapToUpper		INTEGER,
	anxpHardwareTabs	INTEGER,
	anxpCharErase		INTEGER,
	anxpLineErase		INTEGER,
	anxpEraseChar		DisplayString,
	anxpEraseWord		DisplayString,
	anxpEraseLine		DisplayString,
	anxpRedisplayLine	DisplayString,
	anxpToggleOutput	DisplayString,
	anxpTelnetEscape	DisplayString,
	anxpNeedDsr		INTEGER,
	anxpTelnetCRLF		INTEGER,
	anxpLatbEnable		INTEGER,
	anxpSlipSecure		INTEGER,
	anxpNetLocalAddr	IpAddress,
	anxpNetRemoteAddr	IpAddress,
	anxpSlipSubnetMask	IpAddress,
	anxpSlipLoadDumpHost	IpAddress,
	anxpNetMetric		INTEGER,
	anxpSlipAllowDump	INTEGER,
	anxpSlipDoCompression	INTEGER,
	anxpSlipAllowCompression	INTEGER,
	anxpSlipMtuSize		INTEGER,
	anxpSlipNoIcmp		INTEGER,
	anxpSlipTos		INTEGER,
	anxpPppMru		INTEGER,
	anxpPppAcm		INTEGER,
	anxpPppSecurityProto	INTEGER,
	anxpPppUserRemote	DisplayString,
	anxpPppPasswdRemote	DisplayString,
	anxpLatAuthGroupVal	DisplayString,
	anxpPppDialupAddr	INTEGER,
	anxpBanner		INTEGER,
	anxpPsHistory		INTEGER,
	anxpLocation		DisplayString,
	anxpType		INTEGER,
	anxpCliImask7		INTEGER
  }

  anxpPortIndex	OBJECT-TYPE
		SYNTAX INTEGER
		ACCESS read-only 
		STATUS mandatory
		DESCRIPTION
			"A unique number from 1 to totalPorts that 
			identifies each serial port."
		::= { portEntry 1 }

  anxpMode	OBJECT-TYPE
		SYNTAX INTEGER {
			cli(1),
			slave(2),
			adaptive(3),
			unused(4),
			slip(5),
			dedicated(6),
			ppp(7)
		}
		ACCESS read-write 
		STATUS mandatory
		DESCRIPTION
			"This parameter defines the mode for access to
			the serial line port.  The default is cli"
		::= { portEntry 2 }

  anxpCtrlLines	OBJECT-TYPE
		SYNTAX INTEGER {
			none(1),
			dcddtr(2),
			ctsrts(3),
			both(4)
		}
		ACCESS read-write 
		STATUS mandatory
		DESCRIPTION
			"The type of hardware control used on the port:
			modem control (dcddtr), flow control (ctsrts),
			or both."
		::= { portEntry 3 }

  anxpBidirModem  OBJECT-TYPE
		SYNTAX INTEGER {
			enabled(1),
			disabled(2)
		}
		ACCESS read-write 
		STATUS mandatory
		DESCRIPTION
			"This parameter controls whether the port is
			configured for adaptive use with a bidirectional
			modem."
		::= { portEntry 4 }

  anxpAllowBcast  OBJECT-TYPE
		SYNTAX INTEGER {
			enabled(1),
			disabled(2)
		}
		ACCESS read-write 
		STATUS mandatory
		DESCRIPTION
			"Controls whether the serial port can receive
			administrative broadcast messages."
		::= { portEntry 5 }

  anxpBcastDirection  OBJECT-TYPE
		SYNTAX INTEGER {
			port(1),
			network(2)
		}
		ACCESS read-write 
		STATUS mandatory
		DESCRIPTION
			"Defines the direction that an administrative
			broadcast message is sent.  This parameter is
			valid only when the port is defined as a slave
			port by the anxpMode parameter."
		::= { portEntry 6 }

  anxpInputStartChar  OBJECT-TYPE
		SYNTAX DisplayString (SIZE (2))
		ACCESS read-write 
		STATUS mandatory
		DESCRIPTION
			"The control character sequence that restarts
			input if the charPortInFlowType parameter 
			(in the char MIB) is set to xonXoff."
		::= { portEntry 7 }

  anxpInputStopChar  OBJECT-TYPE
		SYNTAX DisplayString (SIZE (2))
		ACCESS read-write 
		STATUS mandatory
		DESCRIPTION
			"The control character sequence that stops
			input if the charPortInFlowType parameter 
			(in the char MIB) is set to xonXoff."
		::= { portEntry 8 }

  anxpOutputStartChar  OBJECT-TYPE
		SYNTAX DisplayString (SIZE (2))
		ACCESS read-write 
		STATUS mandatory
		DESCRIPTION
			"The control character sequence that restarts
			output if the charPortOutFlowType parameter 
			(in the char MIB) is set to xonXoff."
		::= { portEntry 9 }

  anxpOutputStopChar  OBJECT-TYPE
		SYNTAX DisplayString (SIZE (2))
		ACCESS read-write 
		STATUS mandatory
		DESCRIPTION
			"The control character sequence that stops
			output if the charPortOutFlowType parameter 
			(in the char MIB) is set to xonXoff."
		::= { portEntry 10 }

  anxpIxanyFlowCtl  OBJECT-TYPE
		SYNTAX INTEGER {
			enabled(1),
			disabled(2)
		}
		ACCESS read-write 
		STATUS mandatory
		DESCRIPTION
			"This parameter specifies whether any input
			character will be treated as a start (xon)
			character when output has been suspended by
			a stop (xoff) character."
		::= { portEntry 11 }

  anxpLongBreak	OBJECT-TYPE
		SYNTAX INTEGER {
			enabled(1),
			disabled(2)
		}
		ACCESS read-write 
		STATUS mandatory
		DESCRIPTION
			"This parameter controls whether the Annex
			returns the user to the CLI prompt after 
			receiving a break greater than two seconds."
		::= { portEntry 12 }

  anxpShortBreak  OBJECT-TYPE
		SYNTAX INTEGER {
			enabled(1),
			disabled(2)
		}
		ACCESS read-write 
		STATUS mandatory
		DESCRIPTION
			"This parameter controls whether the Annex
			returns the user to the CLI prompt after 
			receiving a break shorter than two seconds."
		::= { portEntry 13 }

  anxpForwardTimer  OBJECT-TYPE
		SYNTAX INTEGER (0..255)
		ACCESS read-write 
		STATUS mandatory
		DESCRIPTION
			"This parameter defines the inter-character
			timer that sets the amount of time, in tens of
			milliseconds, that will elapse before
			forwarding the received data.  The value of
			zero turns off the timer."
		::= { portEntry 14 }

  anxpForwardCount OBJECT-TYPE
		SYNTAX INTEGER (0..255)
		ACCESS read-write 
		STATUS mandatory
		DESCRIPTION
			"Specifies the number of received characters
			buffered for the port by the Annex before
			forwarding the characters to the host or 
			network."
		::= { portEntry 15 }

  anxpImask7Bits  OBJECT-TYPE
		SYNTAX INTEGER {
			enabled(1),
			disabled(2)
		}
		ACCESS read-write 
		STATUS mandatory
		DESCRIPTION
			"When enabled, instructs the Annex to ignore
			the eighth bit of all received characters
			on the port."
		::= { portEntry 16 }

  anxpAttnChar	OBJECT-TYPE
		SYNTAX DisplayString (SIZE (2..32))
		ACCESS read-write 
		STATUS mandatory
		DESCRIPTION
			"Defines a control character sequence as an
			attention character to return the user to
			the CLI prompt.  The Annex-II only allows
			a single control character (eg. ^A), while
			the Annex3 and MicroAnnex allow a string
			of control characters to be defined
			(eg. ^A^B^Z)."
		::= { portEntry 17 }

  anxpInputBufSize  OBJECT-TYPE
		SYNTAX INTEGER (4..255)
		ACCESS read-write 
		STATUS mandatory
		DESCRIPTION
			"The number of 256-byte blocks allocated to
			receive input characters from this port."
		::= { portEntry 18 }

  anxpInputIsActivity	OBJECT-TYPE
		SYNTAX INTEGER {
			enabled(1),
			disabled(2)
		}
		ACCESS read-write 
		STATUS mandatory
		DESCRIPTION
			"Controls whether received input characters
			are considered as activity for the port."
		::= { portEntry 19 }

  anxpOutputIsActivity  OBJECT-TYPE
		SYNTAX INTEGER {
			enabled(1),
			disabled(2)
		}
		ACCESS read-write 
		STATUS mandatory
		DESCRIPTION
			"Controls whether transmitted output characters
			are considered as activity for the port."
		::= { portEntry 20 }

  anxpInactivityTimer  OBJECT-TYPE
		SYNTAX INTEGER (0..255)
		ACCESS read-write 
		STATUS mandatory
		DESCRIPTION
			"The amount of time, in minutes, which a port
			can remain inactive before the Annex terminates
			all sessions and resets the port.  A value of
			0 disables the timer."
		::= { portEntry 21 }

  anxpResetIdleTimer  OBJECT-TYPE
		SYNTAX INTEGER {
			input(1),
			output(2)
		}
		ACCESS read-write 
		STATUS mandatory
		DESCRIPTION
			"Defines whether input or output resets the
			idle timer for the port."
		::= { portEntry 22 }

  anxpCliInactivity  OBJECT-TYPE
		SYNTAX INTEGER (0..255)
		ACCESS read-write 
		STATUS mandatory
		DESCRIPTION
			"The amount of time, in minutes, that the Annex
			waits before hanging up the serial port after
			it becomes idle.  A value of 0 turns off the
			timer.  A value of 255 means immediate, which
			causes the Annex to hang up the port immediately
			after exiting from the last job."
		::= { portEntry 23 }

  anxpCliSecurity  OBJECT-TYPE
		SYNTAX INTEGER {
			enabled(1),
			disabled(2)
		}
		ACCESS read-write 
		STATUS mandatory
		DESCRIPTION
			"This parameter controls whether security is
			enabled for the port."
		::= { portEntry 24 }

  anxpConnectSecurity  OBJECT-TYPE
		SYNTAX INTEGER {
			enabled(1),
			disabled(2)
		}
		ACCESS read-write 
		STATUS mandatory
		DESCRIPTION
			"This parameter controls whether the host-based
			security policy is enabled for access from the 
			port to the network."
		::= { portEntry 25 }

  anxpPortServerSecurity  OBJECT-TYPE
		SYNTAX INTEGER {
			enabled(1),
			disabled(2)
		}
		ACCESS read-write 
		STATUS mandatory
		DESCRIPTION
			"This parameter controls whether the host-based
			security policy is enabled for access to the 
			port from the port server."
		::= { portEntry 26 }

  anxpPortPassword  OBJECT-TYPE
		SYNTAX DisplayString (SIZE (0..15))
		ACCESS read-write 
		STATUS mandatory
		DESCRIPTION
			"This parameter defines a password for the
			port for local password protection."
		::= { portEntry 27 }

  anxpUserName	OBJECT-TYPE
		SYNTAX DisplayString (SIZE (0..16))
		ACCESS read-write 
		STATUS mandatory
		DESCRIPTION
			"A string defining the user name for the
			user of the serial port."
		::= { portEntry 28 }

  anxpDedicatedAddr  OBJECT-TYPE
		SYNTAX IpAddress
		ACCESS read-write 
		STATUS mandatory
		DESCRIPTION
			"When the anxpMode parameter is set to dedicated,
			this parameter defines the Internet address
			of the host to which this port can connect to."
		::= { portEntry 29 }

  anxpDedicatedPort  OBJECT-TYPE
		SYNTAX DisplayString (SIZE (0..16))
		ACCESS read-write 
		STATUS mandatory
		DESCRIPTION
			"The application name or TCP port number to
			which this port can connect when the anxpMode
			parameter is set to dedicated.  The allowed
			application names are 'telnet', 'rlogin',
			'login', 'call', and 'mls'."
		::= { portEntry 30 }

  anxpPrompt	OBJECT-TYPE
		SYNTAX DisplayString (SIZE (0..16))
		ACCESS read-write 
		STATUS mandatory
		DESCRIPTION
			"This parameter defines a port-specific
			prompt."
		::= { portEntry 31 }

  anxpTermVar	OBJECT-TYPE
		SYNTAX DisplayString (SIZE (0..16))
		ACCESS read-write 
		STATUS mandatory
		DESCRIPTION
			"A string defining the type of terminal attached
			to the serial port."
		::= { portEntry 32 }

  anxpNewLineTerm OBJECT-TYPE
		SYNTAX INTEGER {
			enabled(1),
			disabled(2)
		}
		ACCESS read-write 
		STATUS mandatory
		DESCRIPTION
			"This parameter controls whether a carriage
			return is echoed as just a carriage return
			(enabled), or whether the carriage return is
			echoed as a carriage return and line feed."
		::= { portEntry 33 }

  anxpEcho OBJECT-TYPE
		SYNTAX INTEGER {
			enabled(1),
			disabled(2)
		}
		ACCESS read-write 
		STATUS mandatory
		DESCRIPTION
			"This parameter controls whether the Annex 
			echoes all characters as they are received 
			from the port."
		::= { portEntry 34 }

  anxpMapToLower OBJECT-TYPE
		SYNTAX INTEGER {
			enabled(1),
			disabled(2)
		}
		ACCESS read-write 
		STATUS mandatory
		DESCRIPTION
			"When enabled, the Annex translates all upper
			case characters to lower case as they are 
			received from the port."
		::= { portEntry 35 }

  anxpMapToUpper OBJECT-TYPE
		SYNTAX INTEGER {
			enabled(1),
			disabled(2)
		}
		ACCESS read-write 
		STATUS mandatory
		DESCRIPTION
			"When enabled, the Annex translates all lower
			case characters to upper case as they are
			transmitted to the port."
		::= { portEntry 36 }

  anxpHardwareTabs  OBJECT-TYPE
		SYNTAX INTEGER {
			enabled(1),
			disabled(2)
		}
		ACCESS read-write 
		STATUS mandatory
		DESCRIPTION
			"When enabled, this parameter allows the Annex
			to expand ASCII tab characters."
		::= { portEntry 37 }

  anxpCharErase  OBJECT-TYPE
		SYNTAX INTEGER {
			enabled(1),
			disabled(2)
		}
		ACCESS read-write 
		STATUS mandatory
		DESCRIPTION
			"This parameter controls whether the Annex 
			echoes the character erase and word erase 
			characters for a video terminal (enabled) 
			or for a hard-copy terminal (disabled)."
		::= { portEntry 38 }

  anxpLineErase OBJECT-TYPE
		SYNTAX INTEGER {
			enabled(1),
			disabled(2)
		}
		ACCESS read-write 
		STATUS mandatory
		DESCRIPTION
			"This parameter controls whether the Annex 
			echoes the line erase character for a video 
			terminal (enabled) or for a hard-copy terminal 
			(disabled)."
		::= { portEntry 39 }

  anxpEraseChar OBJECT-TYPE
		SYNTAX DisplayString (SIZE (2))
		ACCESS read-write 
		STATUS mandatory
		DESCRIPTION
			"Defines the character erase control character
			sequence."
		::= { portEntry 40 }

  anxpEraseWord OBJECT-TYPE
		SYNTAX DisplayString (SIZE (2))
		ACCESS read-write 
		STATUS mandatory
		DESCRIPTION
			"Defines the word erase control character
			sequence."
		::= { portEntry 41 }

  anxpEraseLine OBJECT-TYPE
		SYNTAX DisplayString (SIZE (2))
		ACCESS read-write 
		STATUS mandatory
		DESCRIPTION
			"Defines the line erase control character
			sequence."
		::= { portEntry 42 }

  anxpRedisplayLine OBJECT-TYPE
		SYNTAX DisplayString (SIZE (2))
		ACCESS read-write 
		STATUS mandatory
		DESCRIPTION
			"Defines the reprint line control character
			sequence."
		::= { portEntry 43 }

  anxpToggleOutput OBJECT-TYPE
		SYNTAX DisplayString (SIZE (2))
		ACCESS read-write 
		STATUS mandatory
		DESCRIPTION
			"Defines the flush control character used to
			flush the output buffer."
		::= { portEntry 44 }

  anxpTelnetEscape OBJECT-TYPE
		SYNTAX DisplayString (SIZE (2))
		ACCESS read-write 
		STATUS mandatory
		DESCRIPTION
			"Defines the control character that returns the
			user to the telnet: prompt when running the
			CLI telnet command."
		::= { portEntry 45 }

  anxpNeedDsr	OBJECT-TYPE
		SYNTAX INTEGER {
			enabled(1),
			disabled(2)
		}
		ACCESS read-write 
		STATUS mandatory
		DESCRIPTION
			"Specifies whether the DSR signal needs to be
			asserted when connecting to a slave port."
		::= { portEntry 46 }

  anxpTelnetCRLF OBJECT-TYPE
		SYNTAX INTEGER {
			enabled(1),
			disabled(2)
		}
		ACCESS read-write
		STATUS mandatory
		DESCRIPTION
			"Defines what characters are transmitted 
			out the port to the network when the 
			End-of-Line character is sensed.  'enabled' 
			means transmit Line-Feed and Carriage-Return.  
			'disabled' means transmit Carriage-Return 
			and NULL.  The default is enabled."
		::= {portEntry 47 }

  anxpLatbEnable	OBJECT-TYPE
		SYNTAX INTEGER {
			enabled(1),
			disabled(2)
		}
		ACCESS read-only 
		STATUS mandatory
		DESCRIPTION
			"Controls interpretation of LAT Data-B packets
			received from host."
		::= { portEntry 48 }

  anxpSlipSecure	OBJECT-TYPE
		SYNTAX INTEGER {
			enabled(1),
			disabled(2)
		}
		ACCESS read-only 
		STATUS mandatory
		DESCRIPTION
			"If anxEnableSecurity is not set, this 
			parameter selects slip session logging.  If 
			anxEnableSecurity is set, this parameter 
			permits slip access only from secure ports."
		::= { portEntry 49 }

  anxpNetLocalAddr  OBJECT-TYPE
		SYNTAX IpAddress
		ACCESS read-write 
		STATUS mandatory
		DESCRIPTION
			"The Internet address for the Annex's side
			of the point-to-point (SLIP or PPP) link."
		::= { portEntry 50 }

  anxpNetRemoteAddr  OBJECT-TYPE
		SYNTAX IpAddress
		ACCESS read-write 
		STATUS mandatory
		DESCRIPTION
			"The Internet address for the host at the
			remote end of the point-to-point (SLIP or PPP) 
			link."
		::= { portEntry 51 }

  anxpSlipSubnetMask  OBJECT-TYPE
		SYNTAX IpAddress
		ACCESS read-write 
		STATUS mandatory
		DESCRIPTION
			"The subnet mask for this SLIP interface."
		::= { portEntry 52 }

  anxpSlipLoadDumpHost  OBJECT-TYPE
		SYNTAX IpAddress
		ACCESS read-write 
		STATUS mandatory
		DESCRIPTION
			"The Internet address of the host from which
			the Annex receives a load or to which the
			Annex sends a dump over the SLIP interface."
		::= { portEntry 53 }

  anxpNetMetric OBJECT-TYPE
		SYNTAX INTEGER (0..64)
		ACCESS read-write 
		STATUS mandatory
		DESCRIPTION
			"This parameter defines the hop count to 
			the remote end of the SLIP or PPP interface."
		::= { portEntry 54 }

  anxpSlipAllowDump  OBJECT-TYPE
		SYNTAX INTEGER {
			enabled(1),
			disabled(2)
		}
		ACCESS read-write 
		STATUS mandatory
		DESCRIPTION
			"This parameter defines whether the Annex is
			allowed to dump across a SLIP link."
		::= { portEntry 55 }

  anxpSlipDoCompression  OBJECT-TYPE
		SYNTAX INTEGER {
			enabled(1),
			disabled(2)
		}
		ACCESS read-write 
		STATUS mandatory
		DESCRIPTION
			"When enabled, the Annex will start TCP/IP
			header compression on this SLIP link."
		::= { portEntry 56 }

  anxpSlipAllowCompression  OBJECT-TYPE
		SYNTAX INTEGER {
			enabled(1),
			disabled(2)
		}
		ACCESS read-write 
		STATUS mandatory
		DESCRIPTION
			"When enabled, the Annex will use TCP/IP
			header compression on this SLIP link only
			if the other end of the SLIP link initiates
			the compression."
		::= { portEntry 57 }

  anxpSlipMtuSize OBJECT-TYPE
		SYNTAX INTEGER {
			large(1),
			small(2)
		}
		ACCESS read-write
		STATUS mandatory
		DESCRIPTION
			"Force the compressed SLIP interface to use
			a Maximum Transmission Unit (MTU) of either 
			1024 bytes (large) or 256 bytes (small).  The
			default is large."
		::= { portEntry 58 }

  anxpSlipNoIcmp  OBJECT-TYPE
		SYNTAX INTEGER {
			enabled(1),
			disabled(2)
		}
		ACCESS read-write 
		STATUS mandatory
		DESCRIPTION
			"When enabled, the Annex will discard any
			ICMP packets directed to this SLIP link."
		::= { portEntry 59 }

  anxpSlipTos	OBJECT-TYPE
		SYNTAX INTEGER {
			enabled(1),
			disabled(2)
		}
		ACCESS read-write 
		STATUS mandatory
		DESCRIPTION
			"When enabled, the Annex sends interactive
			traffic over this SLIP link before any other
			traffic."
		::= { portEntry 60 }

  anxpPppMru    OBJECT-TYPE
		SYNTAX INTEGER (64..1500)
		ACCESS read-write 
		STATUS mandatory
		DESCRIPTION
			"This parameter defines the maximum receive
			unit in bytes.  The default value is 1500."
		::= { portEntry 61 }

  anxpPppAcm    OBJECT-TYPE
		SYNTAX DisplayString  (SIZE (8..10))
		ACCESS read-write 
		STATUS mandatory
		DESCRIPTION
			"This parameter specifies which of the first
			32 bytes (0x00, ... 0x1F) can be sent as
			clear text and which need to be escaped.  A
			bit on in the mask indicates the character
			must be escaped.  The mask should be specified
			as an 8 hex character string (0x1F000000 and
			1F000000 are both acceptable)."
		::= { portEntry 62 }

  anxpPppSecurityProto OBJECT-TYPE
		SYNTAX INTEGER {
			none(1),
			pap(2)
		}
		ACCESS read-write
		STATUS mandatory
		DESCRIPTION
			"Defines which security protocol will be used
			to authenticate the remote user.  This
			parameter must be set and the Annex 
			enable_security (anxEnableSecurity) must be 
			enabled before authentication is performed.  
			The default is none"
		::= { portEntry 63 }

  anxpPppUserRemote	OBJECT-TYPE
		SYNTAX DisplayString (SIZE (0..15))
		ACCESS read-write 
		STATUS mandatory
		DESCRIPTION
			"The username used by the Annex to identify 
			itself if the remote PPP peer asks for 
			authentication.  Reading this parameter
			will return either <set> if the username is
			defined or <unset> if the username is not
			defined."
		::= { portEntry 64 }

  anxpPppPasswdRemote	OBJECT-TYPE
		SYNTAX DisplayString (SIZE (0..15))
		ACCESS read-write 
		STATUS mandatory
		DESCRIPTION
			"The username used by the Annex to identify 
			itself if the remote PPP peer asks for 
			authentication.  Reading this parameter
			will return either <set> if the password is
			defined or <unset> if the password is not
			defined."
		::= { portEntry 65 }

  anxpLatAuthGroupVal	OBJECT-TYPE
		SYNTAX DisplayString (SIZE (32))
		ACCESS read-write 
		STATUS mandatory
		DESCRIPTION
			"This port parameter specifies which remote 
			group codes are accessible to a user on a 
			particular Annex port. Each port has its own 
			set of group codes."
		::= { portEntry 66 }

  anxpPppDialupAddr	OBJECT-TYPE
		SYNTAX INTEGER {
			enabled(1),
			disabled(2)
		}
		ACCESS read-write 
		STATUS mandatory
		DESCRIPTION
			"When enabled, the Annex requests the
			PPP dialup addresses from the host-based
			ACP."
		::= { portEntry 67 }

  anxpBanner	OBJECT-TYPE
		SYNTAX INTEGER {
			enabled(1),
			disabled(2)
		}
		ACCESS read-write
		STATUS mandatory
		DESCRIPTION
			"Specifies whether the Annex banner and message-
			of-the-day are displayed on the port.  The
			default is enabled."
		::= { portEntry 68 }

  anxpPsHistory	OBJECT-TYPE
		SYNTAX INTEGER (0..32767)
		ACCESS read-write
		STATUS mandatory
		DESCRIPTION
			"Specifies how much data to buffer on a slave
			port."
		::= { portEntry 69 }

  anxpLocation	OBJECT-TYPE
		SYNTAX DisplayString (SIZE (0..100))
		ACCESS read-write
		STATUS mandatory
		DESCRIPTION
			"A descriptive string for a this port.  This
			string is displayed by the CLI who command."
		::= { portEntry 70 }

  anxpType	OBJECT-TYPE
		SYNTAX INTEGER {
			dialin(1),
			hardwired(2),
			terminal(3),
			modem(4),
			printer(5)
		}
		ACCESS read-write
		STATUS mandatory
		DESCRIPTION
			"The type of device attached to the port.  The
			default is hardwired."
		::= { portEntry 71 } 

  anxpCliImask7	OBJECT-TYPE
		SYNTAX INTEGER {
			enabled(1),
			disabled(2)
		}
		ACCESS read-write
		STATUS mandatory
		DESCRIPTION
			"Defines whether input at the CLI is masked to
			7 bitx.  The default is disabled."
		::= { portEntry 72 }


  -- the parallel port parameters

  anxpParaPorts	OBJECT-TYPE
		SYNTAX INTEGER
		ACCESS read-only
		STATUS mandatory
		DESCRIPTION
			"The number of parallel ports on this Annex."
		::= { parallelport 1 }

  anxpParaPortTable	OBJECT-TYPE
		SYNTAX SEQUENCE OF AnxpParaPortEntry
		ACCESS not-accessible
		STATUS mandatory
		DESCRIPTION
			"Table of parallel port parameters."
		::= { parallelport 2 }

  anxpParaPortEntry	OBJECT-TYPE
		SYNTAX AnxpParaPortEntry
		ACCESS not-accessible
		STATUS mandatory
		DESCRIPTION
			"The Annex parallel port configuration 
			parameters."
		INDEX  { anxpParaPortIndex }
		::= { anxpParaPortTable 1 }

  AnxpParaPortEntry	::= SEQUENCE {
	anxpParaPortIndex		INTEGER,
	anxpParaPortHardwareTabs	INTEGER,
	anxpParaPortMapToUpper		INTEGER,
	anxpParaPortPrinterWidth	INTEGER,
	anxpParaPortInterface		INTEGER,
	anxpParaPortSpeed		INTEGER
  }

  anxpParaPortIndex	OBJECT-TYPE
		SYNTAX INTEGER
		ACCESS read-only 
		STATUS mandatory
		DESCRIPTION
			"A unique number from 1 to anxpParaPorts that 
			identifies each parallel port."
		::= { anxpParaPortEntry 1 }

  anxpParaPortHardwareTabs OBJECT-TYPE
		SYNTAX INTEGER {
			enabled(1),
			disabled(2)
		}
		ACCESS read-write 
		STATUS mandatory
		DESCRIPTION
			"This parameter controls whether the Annex
			will send a tab character to the printer.  If
			disabled, the tab is replaced with spaces."
		::= { anxpParaPortEntry 2 }

  anxpParaPortMapToUpper  OBJECT-TYPE
		SYNTAX INTEGER {
			enabled(1),
			disabled(2)
		}
		ACCESS read-write 
		STATUS mandatory
		DESCRIPTION
			"When enabled, the Annex translates all lower
			case characters to upper case before 
			transmitting the characters to the printer 
			port."
		::= { anxpParaPortEntry 3 }

  anxpParaPortPrinterWidth  OBJECT-TYPE
		SYNTAX INTEGER (40..132)
		ACCESS read-write 
		STATUS mandatory
		DESCRIPTION
			"The defined maximum number of characters per
			printer line."
		::= { anxpParaPortEntry 4 }

  anxpParaPortInterface OBJECT-TYPE
		SYNTAX INTEGER {
			centronics(1),
			dataproducts(2)
		}
		ACCESS read-write 
		STATUS mandatory
		DESCRIPTION
			"The type of printer attached to the port."
		::= { anxpParaPortEntry 5 }

  anxpParaPortSpeed OBJECT-TYPE
		SYNTAX INTEGER {
			normal(1),
			high-speed(2)
		}
		ACCESS read-write 
		STATUS mandatory
		DESCRIPTION
			"The printer speed on the Micro-Annex."
		::= { anxpParaPortEntry 6 }

  -- the Annex configuration parameters

  anxInetAddr	OBJECT-TYPE
		SYNTAX IpAddress
		ACCESS read-write 
		STATUS mandatory
		DESCRIPTION
			"The Internet address of the Annex."
		::= { annexconfig 1 }

  anxPrefLoadAddr OBJECT-TYPE
		SYNTAX IpAddress
		ACCESS read-write 
		STATUS mandatory
		DESCRIPTION
			"The preferred load address for the Annex."
		::= { annexconfig 2 }

  anxPrefDumpAddr OBJECT-TYPE
		SYNTAX IpAddress
		ACCESS read-write 
		STATUS mandatory
		DESCRIPTION
			"The preferred dump address for the Annex."
		::= { annexconfig 3 }

  anxLoadDumpGateway	OBJECT-TYPE
		SYNTAX IpAddress
		ACCESS read-write 
		STATUS mandatory
		DESCRIPTION
			"The Internet address of a gateway used when
			the preferred load or dump host is on a 
			different network or subnet."
		::= { annexconfig 4 }

  anxLoadDumpSeq  OBJECT-TYPE
		SYNTAX DisplayString (SIZE (0..32))
		ACCESS read-write 
		STATUS mandatory
		DESCRIPTION
			"Lists the available network interfaces and the
			order that the Annex uses them when doing a
			down-line load or up-line dump."
		::= { annexconfig 5 }

  anxLoadBcast	OBJECT-TYPE
		SYNTAX INTEGER {
			enabled(1),	-- load broadcast enabled
			disabled(2)	-- disabled
		}
		ACCESS read-write 
		STATUS mandatory
		DESCRIPTION
			"This parameter defines whether the Annex
			broadcasts for the config or the motd
			files if they were not found on the
			preferred load host."
		::= { annexconfig 6 }

  anxServerCap	OBJECT-TYPE
		SYNTAX DisplayString (SIZE (0..32))
		ACCESS read-write 
		STATUS mandatory
		DESCRIPTION
			"Defines whether the Annex can act as a file
			server host for another Annex.  The 
			allowable values are 'all', 'none' (the
			default), or one or more of the following 
			names separated by commas:
			
			'config', 'motd', 'image'."
		::= { annexconfig 7 }

  anxTimeBcast	OBJECT-TYPE
		SYNTAX INTEGER {
			enabled(1),
			disabled(2)
		}
		ACCESS read-write 
		STATUS mandatory
		DESCRIPTION
			"This parameter defines whether the Annex 
			broadcasts for the time if the preferred load 
			host does not provide a time server."
		::= { annexconfig 8 }

  anxBcastAddr	OBJECT-TYPE
		SYNTAX IpAddress
		ACCESS read-write 
		STATUS mandatory
		DESCRIPTION
			"The Internet address used by the Annex when
			sending broadcasts."
		::= { annexconfig 9 }

  anxSubnetMask	OBJECT-TYPE
		SYNTAX IpAddress
		ACCESS read-write 
		STATUS mandatory
		DESCRIPTION
			"The Internet subnet mask."
		::= { annexconfig 10 }

  anxAuthAgent	OBJECT-TYPE
		SYNTAX INTEGER {
			enabled(1),
			disabled(2)
		}
		ACCESS read-write 
		STATUS mandatory
		DESCRIPTION
			"This parameter controls whether the Annex can
			send an ICMP Address Mask Reply to a received
			ICMP Address Mask Request."
		::= { annexconfig 11 }

  anxMaxVcli	OBJECT-TYPE
		SYNTAX INTEGER (0..255)
		ACCESS read-write 
		STATUS mandatory
		DESCRIPTION
			"The maximum number of virtual CLI connections
			allowed by the Annex at any one time.  0 means
			the Annex does not allow VCLI connections.  255
			allows the Annex to maintain an unlimited number
			of VCLI connections."
		::= { annexconfig 12 }

  anxIpEncapType  OBJECT-TYPE
		SYNTAX INTEGER {
			ethernet(1),
			ieee802(2)
		}
		ACCESS read-write 
		STATUS mandatory
		DESCRIPTION
			"This parameter specifies whether the Annex
			encapsulates IP packets in the Ethernet format
			or the IEEE 802.2/802.3 Data Link Layer format."
		::= { annexconfig 13 }
			
  anxNameServer1Type	OBJECT-TYPE
		SYNTAX INTEGER {
			none(1),
			ien116(2),
			dns(3)
		}
		ACCESS read-write 
		STATUS mandatory
		DESCRIPTION
			"The name service type used by the primary
			nameserver host."
		::= { annexconfig 14 }

  anxNameServer1Addr  OBJECT-TYPE
		SYNTAX IpAddress
		ACCESS read-write 
		STATUS mandatory
		DESCRIPTION
			"The Internet address of the primary 
			nameserver host."
		::= { annexconfig 15 }

  anxNameServer2Type	OBJECT-TYPE
		SYNTAX INTEGER {
			none(1),
			ien116(2),
			dns(3)
		}
		ACCESS read-write 
		STATUS mandatory
		DESCRIPTION
			"The name service type used by the secondary
			nameserver host."
		::= { annexconfig 16 }

  anxNameServer2Addr  OBJECT-TYPE
		SYNTAX IpAddress
		ACCESS read-write 
		STATUS mandatory
		DESCRIPTION
			"The Internet address of the secondary 
			nameserver host."
		::= { annexconfig 17 }

  anxNameServerBcast  OBJECT-TYPE
		SYNTAX INTEGER {
			enabled(1),
			disabled(2)
		}
		ACCESS read-write 
		STATUS mandatory
		DESCRIPTION
			"This parameter controls whether the Annex
			broadcasts a name server request if the 
			preferred name servers do not respond."
		::= { annexconfig 18 }

  anxRwhod	OBJECT-TYPE
		SYNTAX INTEGER {
			enabled(1),
			disabled(2)
		}
		ACCESS read-write 
		STATUS mandatory
		DESCRIPTION
			"Defines whether the Annex listens for RWHO
			broadcasts when building its host table."
		::= { annexconfig 19 }

  anxMinUniqueHostNames  OBJECT-TYPE
		SYNTAX INTEGER {
			enabled(1),
			disabled(2)
		}
		ACCESS read-write 
		STATUS mandatory
		DESCRIPTION
			"Defines whether the Annex minimum uniqueness
			feature is available."
		::= { annexconfig 20 }

  anxHostTableSize  OBJECT-TYPE
		SYNTAX INTEGER (0..251)
		ACCESS read-write 
		STATUS mandatory
		DESCRIPTION
			"Defines the number of entries in the Annex
			host table.  0 indicates no host table.  251
			sets no limit on the size of the table."
		::= { annexconfig 21 }

  anxRouted	OBJECT-TYPE
		SYNTAX INTEGER {
			enabled(1),
			disabled(2)
		}
		ACCESS read-write 
		STATUS mandatory
		DESCRIPTION
			"Defines whether the RIP-listener of the routing
			daemon on the Annex is enabled."
		::= { annexconfig 22 }

  anxEnableSecurity  OBJECT-TYPE
		SYNTAX INTEGER {
			enabled(1),
			disabled(2)
		}
		ACCESS read-write 
		STATUS mandatory
		DESCRIPTION
			"This parameter controls whether the Annex
			security system is enabled."
		::= { annexconfig 23 }

  anxPassword	OBJECT-TYPE
		SYNTAX DisplayString (SIZE (0..15))
		ACCESS read-write 
		STATUS mandatory
		DESCRIPTION
			"Setting this parameter changes the Annex's
			administration password.  Reading this parameter
			will return either <set> if the password is
			defined or <unset> if the password is not
			defined."
		::= { annexconfig 24 }

  anxSecurServer1Addr  OBJECT-TYPE
		SYNTAX IpAddress
		ACCESS read-write 
		STATUS mandatory
		DESCRIPTION
			"The Internet address of the primary host where
			the Annex sends its security requests."
		::= { annexconfig 25 }

  anxSecurServer2Addr  OBJECT-TYPE
		SYNTAX IpAddress
		ACCESS read-write 
		STATUS mandatory
		DESCRIPTION
			"The Internet address of the secondary host 
			where the Annex sends its security requests."
		::= { annexconfig 26 }

  anxNetTurnAround  OBJECT-TYPE
		SYNTAX INTEGER (1..10)
		ACCESS read-write 
		STATUS mandatory
		DESCRIPTION
			"The amount of time (in seconds) that the Annex
			waits for a response from a security server."
		::= { annexconfig 27 }

  anxSecurBcast OBJECT-TYPE
		SYNTAX INTEGER {
			enabled(1),
			disabled(2)
		}
		ACCESS read-write 
		STATUS mandatory
		DESCRIPTION
			"This parameter controls whether the Annex 
			will broadcast its security requests when 
			neither of the preferred security servers are 
			available."
		::= { annexconfig 28 }

  anxVcliSecurity  OBJECT-TYPE
		SYNTAX INTEGER {
			enabled(1),
			disabled(2)
		}
		ACCESS read-write 
		STATUS mandatory
		DESCRIPTION
			"This parameter controls whether the Annex 
			performs user validation on the virtual CLI 
			connections."
		::= { annexconfig 29 }

  anxVcliPassword  OBJECT-TYPE
		SYNTAX DisplayString (SIZE (0..15))
		ACCESS read-write 
		STATUS mandatory
		DESCRIPTION
			"This parameter defines a password used by the 
			Annex when setting up a virtual CLI connection."
		::= { annexconfig 30 }

  anxAcpKey	OBJECT-TYPE
		SYNTAX DisplayString (SIZE (0..15))
		ACCESS read-write 
		STATUS mandatory
		DESCRIPTION
			"This parameter defines the Annex's
			encryption key used when exchanging messages 
			between the Annex and the security server."
		::= { annexconfig 31 }

  anxSysLogMask	OBJECT-TYPE
		SYNTAX DisplayString (SIZE (0..64))
		ACCESS read-write 
		STATUS mandatory
		DESCRIPTION
			"Defines the priority levels of events logged
			in the Annex syslog file.

        		The allowable values are 'all', 'none', or
			one or more of the following level names
			separated by commas:
			
			'emergency', 'alert', 'critical', 'error', 
			'warning', 'notice', 'info', 'debug' "
		::= { annexconfig 32 }

  anxSysLogFacility  OBJECT-TYPE
		SYNTAX INTEGER {
			loglocal0(17),
			loglocal1(18),
			loglocal2(19),
			loglocal3(20),
			loglocal4(21),
			loglocal5(22),
			loglocal6(23),
			loglocal7(24)
		}
		ACCESS read-write 
		STATUS mandatory
		DESCRIPTION
			"This parameter defines the 4.3BSD syslog 
			facility used in logging the Annex messages."
		::= { annexconfig 33 }

  anxSysLogHost OBJECT-TYPE
		SYNTAX IpAddress
		ACCESS read-write 
		STATUS mandatory
		DESCRIPTION
			"The Internet address of the host configured to
			log Annex messages."
		::= { annexconfig 34 }

  anxCliPrompt	OBJECT-TYPE
		SYNTAX DisplayString (SIZE (0..32))
		ACCESS read-write 
		STATUS mandatory
		DESCRIPTION
			"The string used by the Annex to prompt all
			CLI users."
		::= { annexconfig 35 }

  anxMotdFile	OBJECT-TYPE
		SYNTAX DisplayString (SIZE (0..64))
		ACCESS read-write 
		STATUS mandatory
		DESCRIPTION
			"The host file name that contains the 
			message-of-the-day for the Annex."
		::= { annexconfig 36 }

  anxTftpDirName	OBJECT-TYPE
		SYNTAX DisplayString (SIZE (0..64))
		ACCESS read-write
		STATUS mandatory
		DESCRIPTION
			"Specifies the directory name to be prepended
			to all files (boot image, motd, macros, etc.)
			when booting via TFTP."
		::= { annexconfig 37 }

  anxTftpDumpName	OBJECT-TYPE
		SYNTAX DisplayString (SIZE (0..100))
		ACCESS read-write
		STATUS mandatory
		DESCRIPTION
			"The full pathname of the TFTP dump file, if any."
		::= { annexconfig 38 }

  anxTimeZone	OBJECT-TYPE
		SYNTAX INTEGER (-1200..1200)
		ACCESS read-write 
		STATUS mandatory
		DESCRIPTION
			"Defines the timezone where the Annex resides in
			minutes west of GMT."
		::= { annexconfig 39 }

  anxDaylightSavings  OBJECT-TYPE
		SYNTAX INTEGER {
			us(1),
			australian(2),
			westeuropean(3),
			mideuropean(4),
			easteuropean(5),
			canadian(6),
			british(7),
			none(8)
		}
		ACCESS read-write 
		STATUS mandatory
		DESCRIPTION
			"Defines the daylight savings time for the geographic
			location of the Annex."
		::= { annexconfig 40 }

  -- the LAT protocol parameters

  anxLatKey	OBJECT-TYPE
		SYNTAX DisplayString (SIZE (0..32))
		ACCESS read-write 
		STATUS mandatory
		DESCRIPTION
			"The Annex specific LAT key used to enable
			or disable the LAT protocol."
		::= { annexconfig 41 }

  anxCircuitTimer  OBJECT-TYPE
		SYNTAX INTEGER (1..100)
		ACCESS read-write 
		STATUS mandatory
		DESCRIPTION
			"The time interval in tens of milliseconds 
			between the transmission of LAT packets."
		::= { annexconfig 42 }

  anxFacilityNum  OBJECT-TYPE
		SYNTAX INTEGER (0..32767)
		ACCESS read-write 
		STATUS mandatory
		DESCRIPTION
			"The LAT facility number."
		::= { annexconfig 43 }

  anxLatGroupVal	OBJECT-TYPE
		SYNTAX DisplayString (SIZE (32))
		ACCESS read-write 
		STATUS mandatory
		DESCRIPTION
			"The Annex LAT group code for permitting access 
			to LAT services.  To access a specific LAT 
			service, the Annex must have at least one
			enabled group code match the service's set 
			group codes.  The Annex will not maintain any 
			information about unauthorized services.
			
			The value is displayed as a string of hex 
			characters with each bit defining whether a 
			specific group is enabled or disabled."
		::= { annexconfig 44 }

  anxKeepAliveTimer  OBJECT-TYPE
		SYNTAX INTEGER (10..255)
		ACCESS read-write 
		STATUS mandatory
		DESCRIPTION
			"The time interval, in seconds, between the 
			transmission of identification packets during
			times of network inactivity."
		::= { annexconfig 45 }

  anxReXmitLimit  OBJECT-TYPE
		SYNTAX INTEGER (4..120)
		ACCESS read-write 
		STATUS mandatory
		DESCRIPTION
			"The number of times to retransmit a packet
			before notifying the user of a network failure."
		::= { annexconfig 46 }

  anxServerName OBJECT-TYPE
		SYNTAX DisplayString (SIZE (0..16))
		ACCESS read-write 
		STATUS mandatory
		DESCRIPTION
			"A string of up to 16 characters used to name
			the Annex in the LAT protocol."
		::= { annexconfig 47 }

  anxServiceLimit  OBJECT-TYPE
		SYNTAX INTEGER (16..2048)
		ACCESS read-write 
		STATUS mandatory
		DESCRIPTION
			"This parameter defines the upper bound on the
			number of services that the Annex can maintain
			in its local service table."
		::= { annexconfig 48 }

  anxConfigFile  OBJECT-TYPE
		SYNTAX DisplayString (SIZE (0..32))
		ACCESS read-write 
		STATUS mandatory
		DESCRIPTION
			"The name of the host file that contains the alias
			 and menu entries."
		::= { annexconfig 49 }

  anxLatVcliGroupVal  OBJECT-TYPE
		SYNTAX DisplayString (SIZE (32))
		ACCESS read-write 
		STATUS mandatory
		DESCRIPTION
			"This Annex parameter specifies which remote 
			group codes are accessible to virtual cli users.
			All virtual cli users have the same group code.

			The value is displayed as a string of hex 
			characters with each bit defining whether a 
			specific group is enabled or disabled."
		::= { annexconfig 50 }

  anxLatQueueMax OBJECT-TYPE
                SYNTAX INTEGER (0..255)
                ACCESS read-write
                STATUS mandatory
                DESCRIPTION
			"Defines the maximum number of host requests 
			(HIC's) that the Annex will save in its internal 
			queue when the requested resource is not 
			available (port busy)."
		::= { annexconfig 51 }

  anxLatLocation OBJECT-TYPE
		SYNTAX DisplayString (SIZE (0..32))
		ACCESS read-write 
		STATUS mandatory
		DESCRIPTION
			"A string of up to 32 characters used to 
			identify the location of the Annex for
			the LAT protocol."
		::= { annexconfig 52 }

  anxDisabledModules	OBJECT-TYPE
		SYNTAX DisplayString (SIZE (0..64))
		ACCESS read-write 
		STATUS mandatory
		DESCRIPTION
			"Defines which selectable modules are
			currently disabled.  The allowable values 
			are 'all', 'none' or one or more of the 
			following names separated by commas:
			
			'admin', 'lat', 'ppp', 'slip', 'snmp',
			'nameserver', 'cli-edit'.
			
			If this is a MicroAnnex ELS, the values
			'ppp' and 'slip' are not valid."
		::= { annexconfig 53 }

  anxSysLogPort OBJECT-TYPE
                SYNTAX INTEGER (0..64)
                ACCESS read-write
                STATUS mandatory
                DESCRIPTION
			"Specifies the Annex port number where syslog
			messages are sent.  If set to 0, syslog 
			messages are not sent to an Annex port.  This
			is independent of any host-based syslogging
			that may be enabled.  The maximum port number
			allowed will depend on the highest numbered 
			port on the specific Annex."
		::= { annexconfig 54 }


  -- the annex commands

  anxcBoot	OBJECT-TYPE
		SYNTAX INTEGER {
			immediate(1),
			delayed(2),
			dumpboot(3),
			diagnosticboot(4),
			abortschedule(5),
			quiet(6)
		}
		ACCESS read-write 
		STATUS mandatory
		DESCRIPTION
			"The type of boot to be performed.  
			To initiate a dump, this parameter needs to
			be set by the management station.  The values
			stored in anxcBootImage, anxcBootTime, and 
			anxcBootMsg are used as needed, depending on
			the boot type."
		::= { annexcmds 1 }

  anxcBootImage	OBJECT-TYPE
		SYNTAX DisplayString (SIZE (0..100))
		ACCESS read-write
		STATUS mandatory	
		DESCRIPTION
			"The name of the image file to be used with
			the boot command."
		::= { annexcmds 2 }

  anxcBootTime	OBJECT-TYPE
		SYNTAX DisplayString (SIZE (5..10))
		ACCESS read-write 
		STATUS mandatory
		DESCRIPTION
			"The time at which the next boot is scheduled
			in HH:MM format."
		::= { annexcmds 3 }

  anxcBootMsg	OBJECT-TYPE
		SYNTAX DisplayString (SIZE (0..100))
		ACCESS read-write 
		STATUS mandatory
		DESCRIPTION
			"The broadcast message to be displayed when the
			next boot is performed."
		::= { annexcmds 4 }

  anxcReset	OBJECT-TYPE
		SYNTAX INTEGER {
			all(1),
			macros(2),
			motd(3),
			nameserver(4),
			security(5),
			printerport(6),
			serialports(7),
			virtualports(8)
		}
		ACCESS read-write 
		STATUS mandatory
		DESCRIPTION
			"Writing a value to this object causes the
			annex to reset the appropriate subsystem."
		::= { annexcmds 5 }

  anxcBcast	OBJECT-TYPE
		SYNTAX INTEGER {
			all(1),
			serial(2),
			virtual(3)
		}
		ACCESS read-write 
		STATUS mandatory
		DESCRIPTION
			"Writing a value to this object causes the 
			annex to send the message in anxcBcastMsg to the
			specified port set."
		::= { annexcmds 6 }

  anxcBcastMsg	OBJECT-TYPE
		SYNTAX DisplayString (SIZE (0..100))
		ACCESS read-write 
		STATUS mandatory
		DESCRIPTION
			"The message to be broadcast to the Annex
			ports."
		::= { annexcmds 7 }

  END
