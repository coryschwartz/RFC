XYPLEX-MIB DEFINITIONS ::= BEGIN

--                       Definitions of Minimal Managed Objects
--                             for Xyplex Terminal Servers
--          
--                                   21 October 1991
--          
--                          Xyplex Document Number 420-0333-B
--          
--                                     Xyplex, Inc.
--                                330 Codman Hill Road
--                                Boxborough, MA 01719
--          
--                                   (508) 264-9900
--          
--                                 support@xyplex.com
--          
--          

                    IMPORTS
                            enterprises, Counter, TimeTicks
                                    FROM RFC1155-SMI
                            DisplayString
                                    FROM RFC1158-MIB
                            OBJECT-TYPE
                                    FROM RFC-oooo;

            xyplex          OBJECT IDENTIFIER ::= { enterprises 33 }


            system          OBJECT IDENTIFIER ::= { xyplex 1 }


            character       OBJECT IDENTIFIER ::= { xyplex 2 }


            xInternet       OBJECT IDENTIFIER ::= { xyplex 4 }

            --  This MIB module uses the extended OBJECT-TYPE macro as
            --  defined in [9]
            --  this is the private MIB module for Xyplex systems
            -- the System group
            -- Implementation of this group is mandatory for all Xyplex
            -- systems

            sysIdent OBJECT-TYPE
                SYNTAX DisplayString (SIZE (0..40))
                ACCESS read-only
                STATUS mandatory
                DESCRIPTION
                    "An identification string for local and remote 
                    server displays.  Corresponds directly to SERVER 
                    IDENTIFICATION and the value labeled 
                    'Identification:' on the SERVER CHARACTERISTICS 
                    display."
                ::= { system 1 }

            -- the Character group
            -- Implementation of this group is mandatory for all Xyplex
            -- systems with character stream physical ports

            charPhysNumber OBJECT-TYPE
                SYNTAX INTEGER
                ACCESS read-only
                STATUS mandatory
                DESCRIPTION
                    "The number of physical character (terminal) ports 
                    (regardless of their current state) present on this 
                    system."
                ::= { character 1 }

            -- the Physical Character Port table

            charPhysTable OBJECT-TYPE
                SYNTAX SEQUENCE OF CharPhysEntry
                ACCESS not-accessible
                STATUS mandatory
                DESCRIPTION
                    "A list of physical character port entries.  The 
                    number of entries is given by the value of 
                    charPhysNumber."
                ::= { character 2 }


            charPhysEntry OBJECT-TYPE
                SYNTAX CharPhysEntry
                ACCESS not-accessible
                STATUS mandatory
                DESCRIPTION
                    "Status and parameter values for a physical 
                    character port."
                INDEX { charPhysIndex }
                ::= { charPhysTable 1 }

            CharPhysEntry ::=
                SEQUENCE {
                    charPhysIndex
                        INTEGER,
                    charPhysPortName
                        DisplayString,
                    charPhysAdminAccess
                        INTEGER,
                    charPhysOperAccess
                        INTEGER,
                    charPhysBits
                        INTEGER,
                    charPhysParity
                        INTEGER,
                    charPhysSpeed
                        INTEGER,
                    charPhysModemControl
                        INTEGER,
                    charPhysSignalType
                        INTEGER,
                    charPhysInSignalNumber
                        INTEGER,
                    charPhysOutSignalNumber
                        INTEGER,
                    charPhysFlowControl
                        INTEGER,
                    charPhysInFlow
                        INTEGER,
                    charPhysOutFlow
                        INTEGER,
                    charPhysInFlowState
                        INTEGER,
                    charPhysOutFlowState
                        INTEGER,
                    charPhysAutobaud
                        INTEGER,
                    charPhysInCharacters
                        Counter,
                    charPhysOutCharacters
                        Counter,
                    charPhysFramingErrors
                        Counter,
                    charPhysParityErrors
                        Counter,
                    charPhysOverrunErrors
                        Counter,
                    charPhysLastInCharacter
                        INTEGER,
                    charPhysLastOutCharacter
                        INTEGER,
                    charPhysNode
                        DisplayString,
                    charPhysUserName
                        DisplayString
                }

            charPhysIndex OBJECT-TYPE
                SYNTAX INTEGER
                ACCESS read-only
                STATUS mandatory
                DESCRIPTION
                    "A unique value for each physical character port, 
                    directly corresponding to the physical connector.  
                    Its value ranges between 1 and the value of 
                    charPhysNumber."
                ::= { charPhysEntry 1 }


            charPhysPortName OBJECT-TYPE
                SYNTAX DisplayString (SIZE (0..16))
                ACCESS read-write
                STATUS mandatory
                DESCRIPTION
                    "An administratively-assigned name for the port.  If 
                    set to zero length, it becomes the standard, default 
                    name.  Corresponds directly to PORT NAME and the 
                    value labeled 'Name:' in the PORT CHARACTERISTICS 
                    display."
                ::= { charPhysEntry 2 }


            charPhysAdminAccess OBJECT-TYPE
                SYNTAX INTEGER { none(1), dynamic(2), local(3),
                                 remote(4) }
                ACCESS read-write
                STATUS mandatory
                DESCRIPTION
                    "The allowed mode of access to the port.  The value 
                    meanings are:

                    none       not accessed
                    dynamic    local or remote access
                    local      local access only
                    remote     remote access only

                    Corresponds directly to PORT ACCESS and the value 
                    labeled 'Access:' in the PORT CHARACTERISTICS 
                    display."
                ::= { charPhysEntry 3 }


            charPhysOperAccess OBJECT-TYPE
                SYNTAX INTEGER { none(1), local(3), remote(4) }
                ACCESS read-only
                STATUS mandatory
                DESCRIPTION
                    "The current mode of access to the port.

                    none       not accessed
                    local      local access
                    remote     remote access

                    Corresponds directly to the value labeled 'Access:' 
                    in the PORT STATUS display."
                ::= { charPhysEntry 4 }


            charPhysBits OBJECT-TYPE
                SYNTAX INTEGER (7..8)
                ACCESS read-write
                STATUS mandatory
                DESCRIPTION
                    "The port's number of bits per character.  
                    Corresponds directly to PORT CHARACTER SIZE and the 
                    value labeled 'Character Size:' in the PORT 
                    CHARACTERISTICS display."
                ::= { charPhysEntry 5 }


            charPhysParity OBJECT-TYPE
                SYNTAX INTEGER { none(1), even(2), mark(3), odd(4) }
                ACCESS read-write
                STATUS mandatory
                DESCRIPTION
                    "The type of character parity the port provides and 
                    expects.  The value meanings are:

                    none    ignored and not generated
                    even    an even number of 1s
                    mark    always 1
                    odd     an odd number of 1s

                    Corresponds directly to PORT PARITY and the value 
                    labeled 'Parity:' in the PORT CHARACTERISTICS 
                    display."
                ::= { charPhysEntry 6 }


            charPhysSpeed OBJECT-TYPE
                SYNTAX INTEGER
                ACCESS read-write
                STATUS mandatory
                DESCRIPTION
                    "The port's nominal bandwidth in bits per second.  
                    Corresponds directly to PORT SPEED and the value 
                    labeled 'Input Speed:' or 'Output Speed:' in the 
                    PORT CHARACTERISTICS display."
                ::= { charPhysEntry 7 }


            charPhysModemControl OBJECT-TYPE
                SYNTAX INTEGER { disabled(1), enabled(2) }
                ACCESS read-write
                STATUS mandatory
                DESCRIPTION
                    "A control to enable or disable observation of modem 
                    control signals.  Corresponds directly to PORT MODEM 
                    CONTROL and the value labeled 'Modem Control:' in 
                    the PORT CHARACTERISTICS display."
                ::= { charPhysEntry 8 }


            charPhysSignalType OBJECT-TYPE
                SYNTAX INTEGER { rs232(1), centronics(2),
                                 dataproducts(3) }
                ACCESS read-only
                STATUS mandatory
                DESCRIPTION
                    "The port's type of hardware interface.  For RS-232 
                    ports, this is assumed.  For parallel ports, it 
                    corresponds directly to the value labeled 'Printer 
                    Interface:' in the PORT STATUS display."
                ::= { charPhysEntry 9 }


            charPhysInSignalNumber OBJECT-TYPE
                SYNTAX INTEGER
                ACCESS read-only
                STATUS mandatory
                DESCRIPTION
                    "The number of hardware interface signals this port 
                    is capable of observing, indicating the number of 
                    entries for this port in charPhysInSignalTable.  
                    Corresponds directly to the possible values labeled 
                    'Input Signals:' in the PORT STATUS display."
                ::= { charPhysEntry 10 }


            charPhysOutSignalNumber OBJECT-TYPE
                SYNTAX INTEGER
                ACCESS read-only
                STATUS mandatory
                DESCRIPTION
                    "The number of hardware interface signals this port 
                    is capable of asserting, indicating the number of 
                    entries for this port in charPhysOutSignalTable.  
                    Corresponds directly to the possible values labeled 
                    'Output Signals:' in the PORT STATUS display."
                ::= { charPhysEntry 11 }


            charPhysFlowControl OBJECT-TYPE
                SYNTAX INTEGER { none(1), cts(2), dsr(3), xon(4) }
                ACCESS read-write
                STATUS mandatory
                DESCRIPTION
                    "The type of flow control the system applies to the 
                    port for input and output.  The value meanings are:
            none    no flow control
                    cts     CTS/RTS
                    dsr     DCD/DTR/DSR
                    xon     XON/XOFF

                    Directly related to PORT FLOW CONTROL and the value 
                    labeled 'Flow Control:' in the PORT CHARACTERISTICS 
                    display."
                ::= { charPhysEntry 12 }


            charPhysInFlow OBJECT-TYPE
                SYNTAX INTEGER { disabled(1), enabled(2) }
                ACCESS read-write
                STATUS mandatory
                DESCRIPTION
                    "A control for application of flow control to 
                    characters coming into the port.  Corresponds 
                    directly to 'Input Flow Control' in the 'Enabled 
                    Characteristics' section of the PORT CHARACTERISTICS 
                    display."
                ::= { charPhysEntry 13 }


            charPhysOutFlow OBJECT-TYPE
                SYNTAX INTEGER { disabled(1), enabled(2) }
                ACCESS read-write
                STATUS mandatory
                DESCRIPTION
                    "A control for observation of flow control on 
                    characters going out of the port.  Corresponds 
                    directly to 'Output Flow Control' in the 'Enabled 
                    Characteristics' section of the PORT CHARACTERISTICS 
                    display."
                ::= { charPhysEntry 14 }


            charPhysInFlowState OBJECT-TYPE
                SYNTAX INTEGER { go(1), stop(2) }
                ACCESS read-only
                STATUS mandatory
                DESCRIPTION
                    "The dynamic state of flow control as applied by the 
                    system to characters coming into the port.  
                    Corresponds directly to the value labeled 'Input 
                    XOFFed:' in the PORT STATUS display."
                ::= { charPhysEntry 15 }


            charPhysOutFlowState OBJECT-TYPE
                SYNTAX INTEGER { go(1), stop(2) }
                ACCESS read-only
                STATUS mandatory
                DESCRIPTION
                    "The dynamic state of flow control as observed by 
                    the system on characters going out of the port.  
                    Corresponds directly to the value labeled 'Output 
                    XOFFed:' in the PORT STATUS display."
                ::= { charPhysEntry 16 }


            charPhysAutobaud OBJECT-TYPE
                SYNTAX INTEGER { disabled(1), enabled(2) }
                ACCESS read-write
                STATUS mandatory
                DESCRIPTION
                    "A control to allow the port to determine speed 
                    dynamically by looking for carriage return input 
                    characters.  Corresponds directly to 'Autobaud' in 
                    the 'Enabled Characteristics' section of the PORT 
                    CHARACTERISTICS display."
                ::= { charPhysEntry 17 }


            charPhysInCharacters OBJECT-TYPE
                SYNTAX Counter
                ACCESS read-only
                STATUS mandatory
                DESCRIPTION
                    "The total number of characters that have come into 
                    the port.  Corresponds directly to the value labeled 
                    'Input Count:' in the PORT COUNTERS display."
                ::= { charPhysEntry 18 }


            charPhysOutCharacters OBJECT-TYPE
                SYNTAX Counter
                ACCESS read-only
                STATUS mandatory
                DESCRIPTION
                    "The total number of characters that have gone out 
                    of the port.  Corresponds directly to the value 
                    labeled 'Output Count:' in the PORT COUNTERS 
                    display."
                ::= { charPhysEntry 19 }


            charPhysFramingErrors OBJECT-TYPE
                SYNTAX Counter
                ACCESS read-only
                STATUS mandatory
                DESCRIPTION
                    "The total number of characters that have come into 
                    the port with illegally formatted bit frames.  
                    Corresponds directly to the value labeled 'Framing 
                    Errors:' in the PORT COUNTERS display."
                ::= { charPhysEntry 20 }


            charPhysParityErrors OBJECT-TYPE
                SYNTAX Counter
                ACCESS read-only
                STATUS mandatory
                DESCRIPTION
                    "The total number of characters that have come into 
                    the port with invalid parity.  Corresponds directly 
                    to the value labeled 'Parity Errors:' in the PORT 
                    COUNTERS display."
                ::= { charPhysEntry 21 }


            charPhysOverrunErrors OBJECT-TYPE
                SYNTAX Counter
                ACCESS read-only
                STATUS mandatory
                DESCRIPTION
                    "The total number of characters coming into the port 
                    that the system lost due to no room in the port's 
                    input buffer.  Corresponds directly to the value 
                    labeled 'Overrun Errors:' in the PORT COUNTERS 
                    display."
                ::= { charPhysEntry 22 }


            charPhysLastInCharacter OBJECT-TYPE
                SYNTAX INTEGER (0..255)
                ACCESS read-only
                STATUS mandatory
                DESCRIPTION
                    "The character that most recently came into the 
                    port.  Corresponds directly to the value labeled 
                    'Last Char Input:' in the PORT STATUS display."
                ::= { charPhysEntry 23 }


            charPhysLastOutCharacter OBJECT-TYPE
                SYNTAX INTEGER (0..255)
                ACCESS read-only
                STATUS mandatory
                DESCRIPTION
                    "The character that most recently went out of the 
                    port.  Corresponds directly to the value labeled 
                    'Last Char Output:' in the PORT STATUS display."
                ::= { charPhysEntry 24 }


            charPhysNode OBJECT-TYPE
                SYNTAX DisplayString (SIZE (0..16))
                ACCESS read-only
                STATUS mandatory
                DESCRIPTION
                    "An identification for the network system with the 
                    current, active network connection to the port.  
                    Corresponds directly to the value labeled 'Current 
                    Node:' in the PORT STATUS display."
                ::= { charPhysEntry 25 }


            charPhysUserName OBJECT-TYPE
                SYNTAX DisplayString (SIZE (0..16))
                ACCESS read-only
                STATUS mandatory
                DESCRIPTION
                    "An identification of the user logged into the port 
                    on the current, active network connection to the 
                    port.  Corresponds directly to the value following 
                    'Port n:' in the PORT STATUS display."
                ::= { charPhysEntry 26 }

            -- the Physical Character Input Signal table

            charPhysInSignalTable OBJECT-TYPE
                SYNTAX SEQUENCE OF CharPhysInSignalEntry
                ACCESS not-accessible
                STATUS mandatory
                DESCRIPTION
                    "A list of physical character port input hardware 
                    signal entries.  The number of entries is given by 
                    the value of charPhysInSignalNumber"
                ::= { character 3 }


            charPhysInSignalEntry OBJECT-TYPE
                SYNTAX CharPhysInSignalEntry
                ACCESS not-accessible
                STATUS mandatory
                DESCRIPTION
                    "A physical character port hardware signal entry 
                    containing objects for the particular signal on the 
                    particular port."
                INDEX { charInPhysIndex, charInSignalName }
                ::= { charPhysInSignalTable 1 }

            CharPhysInSignalEntry ::=
                SEQUENCE {
                    charInPhysIndex
                        INTEGER,
                    charInSignalName
                        DisplayString,
                    charInSignalState
                        INTEGER
                }

            charInPhysIndex OBJECT-TYPE
                SYNTAX INTEGER
                ACCESS read-only
                STATUS mandatory
                DESCRIPTION
                    "The index value that uniquely identifies the 
                    physical character port to which this signal 
                    belongs.  The port identified by a particular value 
                    of this index is the same port as identified by the 
                    same value of charPhysIndex."
                ::= { charPhysInSignalEntry 1 }

            -- The possible signal names for RS-232 signals are:  DCD,
            -- DTR, DSR, CTS, RTS, and RNG.
            -- The possible signal names for Centronics and Data
            -- Products signals are:  Fault, Power, PaperOut, Busy,
            -- and Online.

            charInSignalName OBJECT-TYPE
                SYNTAX DisplayString (SIZE (1..16))
                ACCESS read-only
                STATUS mandatory
                DESCRIPTION
                    "The name of the hardware signal, as appropriate to 
                    its type."
                ::= { charPhysInSignalEntry 2 }


            charInSignalState OBJECT-TYPE
                SYNTAX INTEGER  { on(1), off(2) }
                ACCESS read-only
                STATUS mandatory
                DESCRIPTION
                    "The current state of the signal.  For RS-232 ports, 
                    corresponds directly to the value labeled 'Input 
                    Signals:' in the PORT STATUS display.  For printer 
                    ports, corresponds to the various signal labels and 
                    values following the label 'Printer Interface:' in 
                    the PORT STATUS display."
                ::= { charPhysInSignalEntry 3 }

            -- the Physical Character Output Signal table

            charPhysOutSignalTable OBJECT-TYPE
                SYNTAX SEQUENCE OF CharPhysOutSignalEntry
                ACCESS not-accessible
                STATUS mandatory
                DESCRIPTION
                    "A list of physical character port output hardware 
                    signal entries.  The number of entries is given by 
                    the value of charPhysOutSignalNumber"
                ::= { character 4 }


            charPhysOutSignalEntry OBJECT-TYPE
                SYNTAX CharPhysOutSignalEntry
                ACCESS not-accessible
                STATUS mandatory
                DESCRIPTION
                    "A physical character port hardware signal entry 
                    containing objects for the particular signal on the 
                    particular port."
                INDEX { charOutPhysIndex, charOutSignalName }
                ::= { charPhysOutSignalTable 1 }

            CharPhysOutSignalEntry ::=
                SEQUENCE {
                    charOutPhysIndex
                        INTEGER,
                    charOutSignalName
                        DisplayString,
                    charOutSignalState
                        INTEGER
                }

            charOutPhysIndex OBJECT-TYPE
                SYNTAX INTEGER
                ACCESS read-only
                STATUS mandatory
                DESCRIPTION
                    "The index value that uniquely identifies the 
                    physical character port to which this signal 
                    belongs.  The port identified by a particular value 
                    of this index is the same port as identified by the 
                    same value of charPhysIndex."
                ::= { charPhysOutSignalEntry 1 }

            -- The possible signal names for RS-232 signals are:  DCD,
            -- DTR, DSR, CTS, RTS, and RNG.
            -- The possible signal names for Centronics and Data
            -- Products signals are:  Fault, Power, PaperOut, Busy,
            -- and Online.

            charOutSignalName OBJECT-TYPE
                SYNTAX DisplayString (SIZE (1..16))
                ACCESS read-only
                STATUS mandatory
                DESCRIPTION
                    "The name of the hardware signal, as appropriate to 
                    its type."
                ::= { charPhysOutSignalEntry 2 }


            charOutSignalState OBJECT-TYPE
                SYNTAX INTEGER  { on(1), off(2) }
                ACCESS read-only
                STATUS mandatory
                DESCRIPTION
                    "The current state of the signal.  For RS-232 ports, 
                    corresponds directly to the value labeled 'Output 
                    Signals:' in the PORT STATUS display.  For printer 
                    ports, corresponds to the various signal labels and 
                    values following the label 'Printer Interface:' in 
                    the PORT STATUS display."
                ::= { charPhysOutSignalEntry 3 }

            -- the Internet group
            -- Implementation of this group is mandatory for all Xyplex
            -- systems that implement Internet protocols

            intDomainSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { xInternet 1 }


            intDomainAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { xInternet 2 }


            intDomainAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { xInternet 3 }


            intGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xInternet 4 }


            intGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xInternet 5 }

            END
