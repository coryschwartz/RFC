-- SCCS version: "@(#)att_efr.mib	4.1.2.3"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T Enhanced Frame Relay MIB for Customer Network Management
--


	ATT-CNM-ENHANCED-FRAME-RELAY-MIB DEFINITIONS ::= BEGIN

	IMPORTS
		enterprises, Gauge
			FROM RFC1155-SMI
		DisplayString
			FROM RFC1213-MIB
		OBJECT-TYPE
			FROM RFC-1212;

	--
	-- Object Identifiers
	--

	att-2		OBJECT IDENTIFIER ::= { enterprises 74 }
	att-products	OBJECT IDENTIFIER ::= { att-2 1 }
	att-mgmt	OBJECT IDENTIFIER ::= { att-2 2 }
	att-cnmAgent	OBJECT IDENTIFIER ::= { att-products 9 }
	att-cnm		OBJECT IDENTIFIER ::= { att-mgmt 15 }
	att-cnm-efr	OBJECT IDENTIFIER ::= { att-cnm 8 }


	--
	-- the Frame Relay group of objects (att-cnm-efr) include:
	--
        --	the Frame Relay Interface-level Configuration table
	--	the Frame Relay Interface-level Measurements table
	--	the Frame Relay PVC-level Configuration table
	--	the Frame Relay PVC-level Measurements table
	--	the Frame Relay PVC-level Status table
	--
	-- NOTE:
	-- This MIB, especially in the configuration tables, refers to
	-- "local" and "remote" devices. These terms are used to identify
	-- devices relative to the interface that is being managed. The
	-- "local" device is the Frame Relay equipment connected to the
	-- interface (port) being managed. The "remote" device refers to
	-- the Frame Relay equipment connected to the interface that will
	-- be at the other end of the call or calls associated with the
	-- PVCs being managed.
	-- 
	-- Also, this MIB refers to originating and terminating endpoints.
	-- These terms are used to identify which DLCI initiates the call.
	-- It does not refer to the device that sends or receives data,
	-- that is independent of the call setup. The originating endpoints
	-- initiate the call, the terminating endpoint only acknowledges,
	-- receives, and completes the call setup process.
	--



        -- the Enhanced-Frame-Relay Interface-level Configuration table

        --
        -- This table provides configuration information
        -- the Frame Relay interfaces supported by this system.
        --

        attCNMefrConfigTable OBJECT-TYPE
                SYNTAX  SEQUENCE OF AttCNMefrConfigEntry
                ACCESS  not-accessible
                STATUS  mandatory
                DESCRIPTION
                        "A list of entries containing configuration
                        information for all Frame Relay interfaces managed by
                        this system."
                ::= { att-cnm-efr 1 }

        attCNMefrConfigEntry OBJECT-TYPE
                SYNTAX  AttCNMefrConfigEntry
                ACCESS  not-accessible
                STATUS  mandatory
                DESCRIPTION
                        "An entry containing configuration information
                        for a particular Frame Relay interface."
                INDEX   { attCNMefrConfigIndex }
                ::= { attCNMefrConfigTable 1 }

        AttCNMefrConfigEntry ::=
                SEQUENCE {
                    attCNMefrConfigIndex
                        INTEGER,
		    attCNMefrMgmtType
			INTEGER,
		    attCNMefrPollDirection
			INTEGER,
		    attCNMefrFullStatusPoll
			INTEGER,
		    attCNMefrErrorThreshold
			INTEGER,
		    attCNMefrMonitoredEvents
			INTEGER,
		    attCNMefrIntegrityTimer
			INTEGER,
		    attCNMefrPollVerifyTimer
			INTEGER,
		    attCNMefrLMIFlowControl
			INTEGER,
		    attCNMefrSupportedPVCs
			INTEGER,
                    attCNMefrMeasMaxIntervals
                        INTEGER,
                    attCNMefrMeasIntervalLen
                        INTEGER
                }

        attCNMefrConfigIndex OBJECT-TYPE
                SYNTAX  INTEGER
                ACCESS  read-only
                STATUS  mandatory
                DESCRIPTION
                        "A unique value for each Frame Relay interface.
			The interface identified by a particular value of
			this index is the same interface as identified by
			the same value of an attCNMifConfigIndex object
			instance."
                ::= { attCNMefrConfigEntry 1 }

        attCNMefrMgmtType OBJECT-TYPE
                SYNTAX  INTEGER {
			   auto-set(1),
			   lmi(2),
			   ansi(3),
			   ccitt(4),
			   none(5)
			}
                ACCESS  read-only
                STATUS  mandatory
                DESCRIPTION
                        "This variable identifies the PVC management scheme
			being used to manage this Frame Relay interface.
			A value of auto-set(1) indicates that the interface
			automatically adopts the scheme being used by the
			access device. A value none(5) indicates that PVC
			management procedures are disabled on this interface."
                ::= { attCNMefrConfigEntry 2 }

        attCNMefrPollDirection OBJECT-TYPE
                SYNTAX  INTEGER {
			   receive(1),
			   send(2),
			   both(3)
			}
                ACCESS  read-only
                STATUS  mandatory
                DESCRIPTION
                        "This variable specifies the role the Frame Relay
			interface performs in a bi-directional PVC
			management scheme. A value of receive(1) means that
			this interface simply responds to Status Enquiries
			and a value of send(2) means that this interface
			initiates Status Enquiries. A value of both(3) means
			that this interface performs both functions.

			This variable applies only if the type of PVC
			management scheme being used is not auto-set (see
			the attCNMefrMgmtType object)."
                ::= { attCNMefrConfigEntry 3 }

        attCNMefrFullStatusPoll OBJECT-TYPE
                SYNTAX  INTEGER
                ACCESS  read-only
                STATUS  mandatory
                DESCRIPTION
                        "This variable identifies the maximum number
			of Status Enquiry intervals that pass before
			issuance of a Full Status Enquiry message.

			This counter is referred to as N391 in the ANSI
			standard.

			This variable applies only if the PVC management
			procedures are enabled. See attCNMefrMgmtType object
			for more details."
                ::= { attCNMefrConfigEntry 4 }

        attCNMefrErrorThreshold OBJECT-TYPE
                SYNTAX  INTEGER
                ACCESS  read-only
                STATUS  mandatory
                DESCRIPTION
                        "This variable identifies the maximum number
			of errored events that can occur before declaring
			the Frame Relay interface down. An errored event
			is the non-receipt of a Status Enquiry, or the
			receipt of a Status Enquiry with an invalid sequence
			number.

			This counter is referred to as N392 in the ANSI
			standard.

			The value for this counter cannot exceed the
			value of the monitored events counter (see the
			attCNMefrMonitoredEvents object)."
                ::= { attCNMefrConfigEntry 5 }

        attCNMefrMonitoredEvents OBJECT-TYPE
                SYNTAX  INTEGER
                ACCESS  read-only
                STATUS  mandatory
                DESCRIPTION
                        "This variable specifies a value 'm', that is used
			with the Error Threshold (attCNMefrErrorThreshold)
			to determine link problems. A link problem is
			declared when the number of errors in the last
			'm' monitored events exceeds the Error Threshold.

			This counter is referred to as N393 in the ANSI
			standard."
                ::= { attCNMefrConfigEntry 6 }

        attCNMefrIntegrityTimer OBJECT-TYPE
                SYNTAX  INTEGER
                ACCESS  read-only
                STATUS  mandatory
                DESCRIPTION
                        "This variable identifies the number of seconds
			between successive Status Enquiry messages.

			This timer is referred to as T391 in the ANSI
			standard.

			This variable is applicable only if this interface
			is configured to be the sender of PVC management
			polls (see the attCNMefrPollDirection object)."
                ::= { attCNMefrConfigEntry 7 }

        attCNMefrPollVerifyTimer OBJECT-TYPE
                SYNTAX  INTEGER
                ACCESS  read-only
                STATUS  mandatory
                DESCRIPTION
                        "This variable specifies the maximum number of
			seconds the Frame Relay interface allows between
			the receipt of Status Enquiries. The expiration
			of this timer is considered to be an errored event.

			This timer is referred to as T392 in the ANSI
			standard.

			This variable is applicable only if this interface is
			configured to be the receiver of PVC management polls.
			Refer to the attCNMefrPollDirection object to verify
			this."
                ::= { attCNMefrConfigEntry 8 }

        attCNMefrLMIFlowControl OBJECT-TYPE
                SYNTAX  INTEGER {
			   lmiFlowControlOn(1),
			   lmiFlowControlOff(2)
			}
                ACCESS  read-only
                STATUS  mandatory
                DESCRIPTION
                        "If the PVC management scheme being used is LMI,
			then this variable indicates whether this Frame
			Relay interface uses XON/XOFF as a means of
			congestion avoidance. 

			This technique is defined in Revision 1.0 of the
			LMI Specification 'Frame Relay Specification with
			Extensions'."
                ::= { attCNMefrConfigEntry 9 }

        attCNMefrSupportedPVCs OBJECT-TYPE
                SYNTAX  INTEGER
                ACCESS  read-only
                STATUS  mandatory
                DESCRIPTION
                        "This variable specifies the number of DLCIs
			currently supported on this Frame Relay interface."
                ::= { attCNMefrConfigEntry 10 }

        attCNMefrMeasMaxIntervals OBJECT-TYPE
                SYNTAX  INTEGER
                ACCESS  read-only
                STATUS  mandatory
                DESCRIPTION
                        "This variable identifies the maximum number
			of measurement intervals supported for the
			measurements maintained by this Frame Relay
			interface in the attCNMefrMeasTable."
                ::= { attCNMefrConfigEntry 11 }

        attCNMefrMeasIntervalLen OBJECT-TYPE
                SYNTAX  INTEGER
                ACCESS  read-only
                STATUS  mandatory
                DESCRIPTION
                        "This variable identifies the number of seconds
			that make up one complete measurement interval for
                        for the measurements maintained by this Frame Relay
                        interface in the attCNMefrMeasTable."
                ::= { attCNMefrConfigEntry 12 }


	-- the Enhanced-Frame-Relay Measurements table

	--
	-- This table provides counts on the various measurement
	-- counts maintained by a Frame Relay interface during
	-- the specified measurement interval.
	--

	attCNMefrMeasTable OBJECT-TYPE
		SYNTAX	SEQUENCE OF AttCNMefrMeasEntry
		ACCESS  not-accessible
		STATUS  mandatory
		DESCRIPTION
			"A list of entries containing measurement counts,
			maintained during the specified measurement interval,
			for all Frame Relay interfaces managed by this
			system."
		::= { att-cnm-efr 2 }

	attCNMefrMeasEntry OBJECT-TYPE
		SYNTAX  AttCNMefrMeasEntry
		ACCESS  not-accessible
		STATUS  mandatory
		DESCRIPTION
			"An entry containing measurement counts, maintained
			during the specified measurement interval, for a
			particular Frame Relay interface."
		INDEX	{ attCNMefrMeasIndex,
			    attCNMefrMeasInterval }
		::= { attCNMefrMeasTable 1 }

	AttCNMefrMeasEntry ::=
		SEQUENCE {
		    attCNMefrMeasIndex
			INTEGER,
		    attCNMefrMeasInterval
			INTEGER,
		    attCNMefrMeasTimeStamp
			INTEGER,
		    attCNMefrMeasLocalTime
			DisplayString,
		    attCNMefrReceivedOctets
			Gauge,
		    attCNMefrSentOctets
			Gauge,
		    attCNMefrReceivedFrames
			Gauge,
		    attCNMefrSentFrames
			Gauge,
		    attCNMefrBadFrames
			Gauge,
		    attCNMefrReceiverOverruns
			Gauge,
		    attCNMefrIngressUtil
			Gauge,
		    attCNMefrEgressUtil
			Gauge
		}

	attCNMefrMeasIndex OBJECT-TYPE
		SYNTAX	INTEGER
		ACCESS	read-only
		STATUS	mandatory
		DESCRIPTION
			"A unique value for each Frame Relay interface.
			The interface identified by a particular value of
			this index is the same interface as identified by
			the same value of an attCNMifConfigIndex object
			instance."
		::= { attCNMefrMeasEntry 1 }

	attCNMefrMeasInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval.

                        The value of XX is specified by the
                        attCNMefrMeasMaxIntervals object given in the
                        attCNMefrConfigTable.

                        The maximum length of each measurement interval is
                        specified by the attCNMefrMeasIntervalLen object given
                        in the attCNMefrConfigTable."
		::= { attCNMefrMeasEntry 2 }

	attCNMefrMeasTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMefrMeasEntry 3 }

	attCNMefrMeasLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMefrMeasEntry 4 }

	attCNMefrReceivedOctets OBJECT-TYPE
		SYNTAX	Gauge
		ACCESS	read-only
		STATUS	mandatory
		DESCRIPTION
			"The counter associated with the number of bytes
			received by this Frame Relay interface during the
			specified measurement interval."
		::= { attCNMefrMeasEntry 5 }

	attCNMefrSentOctets OBJECT-TYPE
		SYNTAX	Gauge
		ACCESS	read-only
		STATUS	mandatory
		DESCRIPTION
			"The counter associated with the number of bytes
			sent by this Frame Relay interface during the
			specified measurement interval."
		::= { attCNMefrMeasEntry 6 }

	attCNMefrReceivedFrames OBJECT-TYPE
		SYNTAX	Gauge
		ACCESS	read-only
		STATUS	mandatory
		DESCRIPTION
			"The counter associated with the number of frames
			received by this Frame Relay interface during the
			specified measurement interval."
		::= { attCNMefrMeasEntry 7 }

	attCNMefrSentFrames OBJECT-TYPE
		SYNTAX	Gauge
		ACCESS	read-only
		STATUS	mandatory
		DESCRIPTION
			"The counter associated with the number of frames
			sent by this Frame Relay interface during the
			specified measurement interval."
		::= { attCNMefrMeasEntry 8 }

	attCNMefrBadFrames OBJECT-TYPE
		SYNTAX	Gauge
		ACCESS	read-only
		STATUS	mandatory
		DESCRIPTION
			"The counter associated with the number of frames
			received by this Frame Relay interface that are
			faulty. The interface discards bad frames received.

			A bad frame could be a frame with a non-integral
			number of octets, or an aborted frame, or a frame
			with a bad Frame Check Sequence (FCS), or a frame
			that exceeds the maximum frame size."
		::= { attCNMefrMeasEntry 9 }

	attCNMefrReceiverOverruns OBJECT-TYPE
		SYNTAX	Gauge
		ACCESS	read-only
		STATUS	mandatory
		DESCRIPTION
			"The counter associated with the number of receiver
			overruns occurred at this Frame Relay interface
			during the specified measurement interval.

			A receiver overrun occurs when frames are received
			faster than they can be stored and forwarded."
		::= { attCNMefrMeasEntry 10 }

	attCNMefrIngressUtil OBJECT-TYPE
		SYNTAX	Gauge
		ACCESS	read-only
		STATUS	mandatory
		DESCRIPTION
			"The counter associated with the utilization level
			of the Frame Relay interface, derived as the total
			bytes received (in the ingress direction) divided by
			the line speed of the interface, over the measurement
			interval."
		::= { attCNMefrMeasEntry 11 }

	attCNMefrEgressUtil OBJECT-TYPE
		SYNTAX	Gauge
		ACCESS	read-only
		STATUS	mandatory
		DESCRIPTION
			"The counter associated with the utilization level
			of the Frame Relay interface, derived as the total
			bytes sent (in the egress direction) divided by the
			line speed of the interface, over the measurement
			interval."
		::= { attCNMefrMeasEntry 12 }


        -- the Enhanced Frame Relay PVC-level Configuration table

        --
        -- This table provides PVC-level configuration information
        -- for the Frame Relay interfaces supported by this system.
        --

        attCNMefrPVCConfigTable OBJECT-TYPE
                SYNTAX  SEQUENCE OF AttCNMefrPVCConfigEntry
                ACCESS  not-accessible
                STATUS  mandatory
                DESCRIPTION
                        "A list of entries containing configuration
                        information for all Frame Relay interfaces managed by
                        this system."
                ::= { att-cnm-efr 3 }

        attCNMefrPVCConfigEntry OBJECT-TYPE
                SYNTAX  AttCNMefrPVCConfigEntry
                ACCESS  not-accessible
                STATUS  mandatory
                DESCRIPTION
                        "An entry containing configuration information
                        for a particular Frame Relay interface."
                INDEX   { attCNMefrPVCConfigIfIndex,
				attCNMefrPVCConfigIndex }
                ::= { attCNMefrPVCConfigTable 1 }

        AttCNMefrPVCConfigEntry ::=
                SEQUENCE {
                    attCNMefrPVCConfigIfIndex
                        INTEGER,
                    attCNMefrPVCConfigIndex
                        INTEGER,
		    attCNMefrPVCServiceType
			INTEGER,
		    attCNMefrLocalCIR
			INTEGER,
		    attCNMefrLocalCommittedBurst
			INTEGER,
		    attCNMefrLocalExcessBurst
			INTEGER,
		    attCNMefrRemoteCIR
			INTEGER,
		    attCNMefrRemoteCommittedBurst
			INTEGER,
		    attCNMefrRemoteExcessBurst
			INTEGER,
		    attCNMefrMulticastGroup1
			INTEGER,
		    attCNMefrMulticastGroup2
			INTEGER,
		    attCNMefrMulticastGroup3
			INTEGER,
		    attCNMefrMulticastGroup4
			INTEGER,
                    attCNMefrPVCMeasMaxIntervals
                        INTEGER,
                    attCNMefrPVCMeasIntervalLen
                        INTEGER
                }

        attCNMefrPVCConfigIfIndex OBJECT-TYPE
                SYNTAX  INTEGER
                ACCESS  read-only
                STATUS  mandatory
                DESCRIPTION
                        "A unique value for each Frame Relay interface.
			The interface identified by a particular value of
			this index is the same interface as identified by
			the same value of an attCNMifConfigIndex object
			instance."
                ::= { attCNMefrPVCConfigEntry 1 }

        attCNMefrPVCConfigIndex OBJECT-TYPE
                SYNTAX  INTEGER
                ACCESS  read-only
                STATUS  mandatory
                DESCRIPTION
			"The DLCI number on a Frame Relay interface that
			identifies a unique Data Link Connection."
                ::= { attCNMefrPVCConfigEntry 2 }

        attCNMefrPVCServiceType OBJECT-TYPE
                SYNTAX  INTEGER {
			   unicast(1),
			   multicast(2)
			}
                ACCESS  read-only
                STATUS  mandatory
                DESCRIPTION
			"This variable specifies whether the DLCI is a
			multicast or PVC (unicast) DLCI. A PVC DLCI is 
			used to connect a specific endpoint to another
			endpoint, whereas a multicast DLCI allows an
			endpoint to transmit single frames to this Frame
			Relay interface and have them delivered to multiple
			destinations."
                ::= { attCNMefrPVCConfigEntry 3 }

        attCNMefrLocalCIR OBJECT-TYPE
                SYNTAX  INTEGER
                ACCESS  read-only
                STATUS  mandatory
                DESCRIPTION
			"This variable specifies the Committed Information
			Rate (CIR) for data transmitted on this PVC from
			the local device through the network via this Frame
			Relay interface. The maximum value for the CIR is
			limited to the line speed of this interface."
                ::= { attCNMefrPVCConfigEntry 4 }

        attCNMefrLocalCommittedBurst OBJECT-TYPE
                SYNTAX  INTEGER
                ACCESS  read-only
                STATUS  mandatory
                DESCRIPTION
			"This variable specifies the Committed Burst (Bc)
			for data transmitted on this PVC from the local
			device through the network via this Frame Relay
			interface."
                ::= { attCNMefrPVCConfigEntry 5 }

        attCNMefrLocalExcessBurst OBJECT-TYPE
                SYNTAX  INTEGER
                ACCESS  read-only
                STATUS  mandatory
                DESCRIPTION
			"This variable specifies the Excess Burst (Be)
			for data transmitted on this PVC from the local
			device through the network via this Frame Relay
			interface."
                ::= { attCNMefrPVCConfigEntry 6 }

        attCNMefrRemoteCIR OBJECT-TYPE
                SYNTAX  INTEGER
                ACCESS  read-only
                STATUS  mandatory
                DESCRIPTION
			"This variable specifies the Committed Information
			Rate (CIR) for data transmitted on this PVC from
			the remote device, through the network, to the local
			device via this Frame Relay interface. The maximum
			value for the CIR is limited to the line speed of
			this interface."
                ::= { attCNMefrPVCConfigEntry 7 }

        attCNMefrRemoteCommittedBurst OBJECT-TYPE
                SYNTAX  INTEGER
                ACCESS  read-only
                STATUS  mandatory
                DESCRIPTION
			"This variable specifies the Committed Burst (Bc)
			for data transmitted on this PVC from the remote
			device, through the network, to the local device
			via this Frame Relay interface."
                ::= { attCNMefrPVCConfigEntry 8 }

        attCNMefrRemoteExcessBurst OBJECT-TYPE
                SYNTAX  INTEGER
                ACCESS  read-only
                STATUS  mandatory
                DESCRIPTION
			"This variable specifies the Excess Burst (Be)
			for data transmitted on this PVC from the remote
			device, through the network, to the local device
			via this Frame Relay interface."
                ::= { attCNMefrPVCConfigEntry 9 }

	attCNMefrMulticastGroup1 OBJECT-TYPE
                SYNTAX  INTEGER
                ACCESS  read-only
                STATUS  mandatory
                DESCRIPTION
			"A multicast (group) DLCI that includes this
			DLCI as one of its members. Any messages
			addressed to this multicast DLCI will
			be sent to this PVC and to other PVCs that
			belong in this group.

			A unicast DLCI can be a member of at most 4 groups.
			This variable identifies the first multicast DLCI
			that includes this DLCI as its member."
                ::= { attCNMefrPVCConfigEntry 10 }
		
	attCNMefrMulticastGroup2 OBJECT-TYPE
                SYNTAX  INTEGER
                ACCESS  read-only
                STATUS  mandatory
                DESCRIPTION
			"A multicast (group) DLCI that includes this
			DLCI as one of its members. Any messages
			addressed to this multicast DLCI will
			be sent to this PVC and to other PVCs that
			belong in this group.

			A unicast DLCI can be a member of at most 4 groups.
			This variable identifies the second multicast DLCI
			that includes this DLCI as its member."
                ::= { attCNMefrPVCConfigEntry 11 }
		
	attCNMefrMulticastGroup3 OBJECT-TYPE
                SYNTAX  INTEGER
                ACCESS  read-only
                STATUS  mandatory
                DESCRIPTION
			"A multicast (group) DLCI that includes this
			DLCI as one of its members. Any messages
			addressed to this multicast DLCI will
			be sent to this PVC and to other PVCs that
			belong in this group.

			A unicast DLCI can be a member of at most 4 groups.
			This variable identifies the third multicast DLCI
			that includes this DLCI as its member."
                ::= { attCNMefrPVCConfigEntry 12 }
		
	attCNMefrMulticastGroup4 OBJECT-TYPE
                SYNTAX  INTEGER
                ACCESS  read-only
                STATUS  mandatory
                DESCRIPTION
			"A multicast (group) DLCI that includes this
			DLCI as one of its members. Any messages
			addressed to this multicast DLCI will
			be sent to this PVC and to other PVCs that
			belong in this group.

			A unicast DLCI can be a member of at most 4 groups.
			This variable identifies the fourth multicast DLCI
			that includes this DLCI as its member."
                ::= { attCNMefrPVCConfigEntry 13 }
		
        attCNMefrPVCMeasMaxIntervals OBJECT-TYPE
                SYNTAX  INTEGER
                ACCESS  read-only
                STATUS  mandatory
                DESCRIPTION
                        "This variable identifies the maximum number
			of measurement intervals supported for the
			measurements maintained by this Frame Relay
			interface in the attCNMefrPVCMeasTable."
                ::= { attCNMefrPVCConfigEntry 14 }

        attCNMefrPVCMeasIntervalLen OBJECT-TYPE
                SYNTAX  INTEGER
                ACCESS  read-only
                STATUS  mandatory
                DESCRIPTION
                        "This variable identifies the number of seconds
			that make up one complete measurement interval for
                        for the measurements maintained by this Frame Relay
                        interface in the attCNMefrPVCMeasTable."
                ::= { attCNMefrPVCConfigEntry 15 }


	-- the Frame Relay PVC-level Measurements table

	--
	-- This table provides counts on the various PVC-level
	-- measurement counts maintained by a Frame Relay interface
	-- during the specified measurement interval.
	--

	attCNMefrPVCMeasTable OBJECT-TYPE
		SYNTAX	SEQUENCE OF AttCNMefrPVCMeasEntry
		ACCESS  not-accessible
		STATUS  mandatory
		DESCRIPTION
			"A list of entries containing PVC-level measurement
			counts, maintained during the specified measurement
			interval, for all the Frame Relay interfaces managed
			by this system."
		::= { att-cnm-efr 4 }

	attCNMefrPVCMeasEntry OBJECT-TYPE
		SYNTAX  AttCNMefrPVCMeasEntry
		ACCESS  not-accessible
		STATUS  mandatory
		DESCRIPTION
			"An entry containing measurement counts, maintained
			during the specified measurement interval, for a
			particular PVC on a specific Frame Relay interface."
		INDEX	{ attCNMefrPVCMeasIfIndex,
			    attCNMefrPVCMeasIndex,
			      attCNMefrPVCMeasInterval }
		::= { attCNMefrPVCMeasTable 1 }

	AttCNMefrPVCMeasEntry ::=
		SEQUENCE {
		    attCNMefrPVCMeasIfIndex
			INTEGER,
		    attCNMefrPVCMeasIndex
			INTEGER,
		    attCNMefrPVCMeasInterval
			INTEGER,
		    attCNMefrPVCMeasTimeStamp
			INTEGER,
		    attCNMefrPVCMeasLocalTime
			DisplayString,
		    attCNMefrPVCReceivedFrames
			Gauge,
		    attCNMefrPVCSentFrames
			Gauge,
		    attCNMefrDiscardEligibilityFrames
			Gauge,
		    attCNMefrBurstSizeExceeded
			Gauge,
		    attCNMefrCongestionAtIngress
			Gauge,
		    attCNMefrCongestionAtEgress
			Gauge
		}

	attCNMefrPVCMeasIfIndex OBJECT-TYPE
		SYNTAX	INTEGER
		ACCESS	read-only
		STATUS	mandatory
		DESCRIPTION
			"A unique value for each Frame Relay interface.
			The interface identified by a particular value of
			this index is the same interface as identified by
			the same value of an attCNMifConfigIndex object
			instance."
		::= { attCNMefrPVCMeasEntry 1 }

	attCNMefrPVCMeasIndex OBJECT-TYPE
		SYNTAX	INTEGER
		ACCESS	read-only
		STATUS	mandatory
		DESCRIPTION
			"The DLCI number on a Frame Relay interface that
			identifies a unique Data Link Connection."
		::= { attCNMefrPVCMeasEntry 2 }

	attCNMefrPVCMeasInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval."
		::= { attCNMefrPVCMeasEntry 3 }

	attCNMefrPVCMeasTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMefrPVCMeasEntry 4 }

	attCNMefrPVCMeasLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMefrPVCMeasEntry 5 }

	attCNMefrPVCReceivedFrames OBJECT-TYPE
		SYNTAX	Gauge
		ACCESS	read-only
		STATUS	mandatory
		DESCRIPTION
			"The counter associated with the number of
			frames received by this Frame Relay PVC during
			the specified measurement interval."
		::= { attCNMefrPVCMeasEntry 6 }

	attCNMefrPVCSentFrames OBJECT-TYPE
		SYNTAX	Gauge
		ACCESS	read-only
		STATUS	mandatory
		DESCRIPTION
			"The counter associated with the number of
			frames sent by this Frame Relay PVC during
			the specified measurement interval."
		::= { attCNMefrPVCMeasEntry 7 }

	attCNMefrDiscardEligibilityFrames OBJECT-TYPE
		SYNTAX	Gauge
		ACCESS	read-only
		STATUS	mandatory
		DESCRIPTION
			"The counter associated with the number of
			ingress frames received by this PVC that exceed
			the Committed Burst Size but don't exceed the
			maximum throughput configured for the PVC (the
			Committed Burst Size plus the Excess Burst Size).
			In addition, all ingress frames with the Discard
			Eligible (DE) Indicator bit set are included
			in this count."
		::= { attCNMefrPVCMeasEntry 8 }

	attCNMefrBurstSizeExceeded OBJECT-TYPE
		SYNTAX	Gauge
		ACCESS	read-only
		STATUS	mandatory
		DESCRIPTION
			"The counter associated with the number of
			frames that were discarded due to exceeding the
			maximum throughput configured for the PVC (the
			Committed Burst Size plus the Excess Burst Size).
			If the Committed Information Rate (CIR) has not
			been configured for the PVC, then this field is
			not applicable."
		::= { attCNMefrPVCMeasEntry 9 }

	attCNMefrCongestionAtIngress OBJECT-TYPE
		SYNTAX	Gauge
		ACCESS	read-only
		STATUS	mandatory
		DESCRIPTION
			"The counter associated with the number of times
			frames received by this PVC had to be discarded
			because buffers were unavailable or congestion
			control was being enforced during the specified
			measurement interval."
		::= { attCNMefrPVCMeasEntry 10 }

	attCNMefrCongestionAtEgress OBJECT-TYPE
		SYNTAX	Gauge
		ACCESS	read-only
		STATUS	mandatory
		DESCRIPTION
			"The counter associated with the number of times
			frames sent by this PVC had to be discarded
			because buffers were unavailable or congestion
			control was being enforced during the specified
			measurement interval."
		::= { attCNMefrPVCMeasEntry 11 }


	-- the Frame Relay PVC-level Status table

	--
	-- This table provides status information on
	-- Data Link Connections on all Frame Relay interfaces
	-- supported by this system.
	--

	attCNMefrPVCStatusTable OBJECT-TYPE
		SYNTAX	SEQUENCE OF AttCNMefrPVCStatusEntry
		ACCESS  not-accessible
		STATUS  mandatory
		DESCRIPTION
			"A list of entries containing status information
			about Data Link Connections on Frame Relay interfaces
			managed by this system."
		::= { att-cnm-efr 5 }

	attCNMefrPVCStatusEntry OBJECT-TYPE
		SYNTAX  AttCNMefrPVCStatusEntry
		ACCESS  not-accessible
		STATUS  mandatory
		DESCRIPTION
			"An entry containing status information about
			a particular Data Link Connection on a specific
			Frame Relay interface."
		INDEX	{ attCNMefrPVCStatusIfIndex,
			    attCNMefrPVCStatusIndex }
		::= { attCNMefrPVCStatusTable 1 }

	AttCNMefrPVCStatusEntry ::=
		SEQUENCE {
		    attCNMefrPVCStatusIfIndex
			INTEGER,
		    attCNMefrPVCStatusIndex
			INTEGER,
		    attCNMefrPVCAdminStatus
			INTEGER,
		    attCNMefrPVCOperStatus
			INTEGER
		}

	attCNMefrPVCStatusIfIndex OBJECT-TYPE
		SYNTAX	INTEGER
		ACCESS	read-only
		STATUS	mandatory
		DESCRIPTION
			"A unique value for each Frame Relay interface.
			The interface identified by a particular value of
			this index is the same interface as identified by
			the same value of an attCNMifConfigIndex object
			instance."
		::= { attCNMefrPVCStatusEntry 1 }

	attCNMefrPVCStatusIndex OBJECT-TYPE
		SYNTAX	INTEGER
		ACCESS	read-only
		STATUS	mandatory
		DESCRIPTION
			"The DLCI number on a Frame Relay interface that
			identifies a unique Data Link Connection."
		::= { attCNMefrPVCStatusEntry 2 }

	attCNMefrPVCAdminStatus OBJECT-TYPE
		SYNTAX  INTEGER {
			    up(1),
			    down(2),
			    testing(3),
			    unknown(4)
			}
		ACCESS  read-only
		STATUS  mandatory
		DESCRIPTION
			"The desired state of this Data Link Connection."
		::= { attCNMefrPVCStatusEntry 3 }

	attCNMefrPVCOperStatus OBJECT-TYPE
		SYNTAX  INTEGER {
			    up(1),
			    down(2),
			    testing(3),
			    unknown(4)
			}
		ACCESS  read-only
		STATUS  mandatory
		DESCRIPTION
			"The current operational state of this Data Link
			Connection."
		::= { attCNMefrPVCStatusEntry 4 }

	END
