------------------------------- Referenced Note ---------------------------
--

-- Copyright (c) 1994 International Business Machines Corp.
-- All Rights Reserved.
--

-- Copyright (c) 1994 Chipcom Corporation.  All Rights Reserved.
--
-- Reproduction of this document is authorized on condition that this
-- copyright notice is included.  This SNMP MIB Specification
-- embodies proprietary intellectual property.  The copyright
-- retains all title and ownership in the specification, including any
-- revisions.
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call
-- the AIX Support Center (1-800-237-5511).
--

--
-- MIB Version Information:
--
-- Version     Description
------------------------------------------------------------------
--   v1.0      Initial version of the mib02 branch.
--   v2.0      Version tracking initiated.
--   v2.1      Version release with TRMM v.2.10
--   v2.2      Version release with EMM v4.0
--   v2.3      Version release with TRMM v.3.0
--   v2.39     Version release with DMM v.1.0 and FMM b.2.00
--   v2.4      Version release with FMM v.2.0
--


CHIPCOMMIB DEFINITIONS ::= BEGIN
IMPORTS
	enterprises, IpAddress, Counter, Gauge, TimeTicks FROM RFC1155-SMI
	OBJECT-TYPE		FROM RFC-1212
	DisplayString		FROM RFC1213-MIB
	TRAP-TYPE		FROM RFC-1215;

-- All representations of MAC addresses in this MIB Module use,
-- as a textual convention (i.e. this convention does not affect
-- their encoding), the data type:

MacAddress ::= OCTET STRING (SIZE (6))    -- a 6 octet address in
					  -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.

-- #include "dot1.h"


chipcom		OBJECT IDENTIFIER ::= { enterprises 49 }

mib02	OBJECT IDENTIFIER ::= { chipcom 2 }

--
-- Top level groups
--

gen	OBJECT IDENTIFIER ::= { mib02 1 }
echo	OBJECT IDENTIFIER ::= { mib02 2 }
products	OBJECT IDENTIFIER ::= { mib02 3 }
experiment  OBJECT IDENTIFIER ::= { mib02 4 }
tty		OBJECT IDENTIFIER ::= { mib02 5 }
tftp	OBJECT IDENTIFIER ::= { mib02 6 }
download	OBJECT IDENTIFIER ::= { mib02 7 }
alert	    OBJECT IDENTIFIER ::= { mib02 8 }


bootp	OBJECT IDENTIFIER ::= { mib02 11 }

--
-- Product specific branches.  Also used for sysObjectID.
--

hub		OBJECT IDENTIFIER ::= { products 1 }
ebm		OBJECT IDENTIFIER ::= { products 2 }

emm		OBJECT IDENTIFIER ::= { products 5 }
bridge  OBJECT IDENTIFIER ::= { products 6 }
trmm		OBJECT IDENTIFIER ::= { products 7 }
fmm		OBJECT IDENTIFIER ::= { products 8 }
focus1		OBJECT IDENTIFIER ::= { products 9 }
eim	OBJECT IDENTIFIER ::= { products 10 }
hub8260		OBJECT IDENTIFIER ::= { products 11 }
dmm		OBJECT IDENTIFIER ::= { products 12 }


--
-- Experimental Branches
--
-- When RFCs are still in the experimental stage, the MIB
-- is incorporated under the enterprise experimental branch
-- so that changes in the experimental MIB do not affect
-- the released product.
--
-- As the RFC becomes standard and support is provided by the agents,
-- the support under this branch will be moved to the appropriate
-- standard branch.  That is, the support under this branch
-- for the MIB in question will be removed.
--

expTokenRing OBJECT IDENTIFIER ::= { experiment 1 }
dot1dBridge	OBJECT IDENTIFIER ::= { experiment 14 }
dot5	     OBJECT IDENTIFIER ::= { expTokenRing 1 }

--
-- Hub Groups
--

agents		OBJECT IDENTIFIER ::= { hub   1 }
conc		OBJECT IDENTIFIER ::= { hub   2 }
env		OBJECT IDENTIFIER ::= { hub   3 }
modules		OBJECT IDENTIFIER ::= { hub   4 }
nets	OBJECT IDENTIFIER ::= { hub   5 }
groups		OBJECT IDENTIFIER ::= { hub   6 }
alarm		OBJECT IDENTIFIER ::= { hub   7 }
ocPower		OBJECT IDENTIFIER ::= { hub   8 }
ocPowerControl  OBJECT IDENTIFIER ::= { ocPower  1 }
ocInventory	OBJECT IDENTIFIER ::= { hub   9 }
ocInvHub	OBJECT IDENTIFIER ::= { ocInventory 1 }
ocInvMods	OBJECT IDENTIFIER ::= { ocInventory 2 }

pS2	      OBJECT IDENTIFIER ::= { hub	11 }



--
-- Value added module attributes
--

specMods	OBJECT IDENTIFIER ::= { modules 4 }

--
-- A node for each module type  :
--

cnnNSCTL	OBJECT IDENTIFIER ::= { specMods 3 }
ennMSMGT	OBJECT IDENTIFIER ::= { specMods 4 }
ennMSFIB	OBJECT IDENTIFIER ::= { specMods 5 }
ennMSUTP	OBJECT IDENTIFIER ::= { specMods 6 }
ennMSRJ45S	OBJECT IDENTIFIER ::= { specMods 7 }
ennMSBNC	OBJECT IDENTIFIER ::= { specMods 8 }
eennPSBRG	OBJECT IDENTIFIER ::= { specMods 9 }
esnnPSRTR	OBJECT IDENTIFIER ::= { specMods 10 }
eennPSRTR	OBJECT IDENTIFIER ::= { specMods 11 }
ennPSAUIF	OBJECT IDENTIFIER ::= { specMods 12 }
ennPSAUIM	OBJECT IDENTIFIER ::= { specMods 13 }
t08MSRJ45S	OBJECT IDENTIFIER ::= { specMods 14 }
ennPSFIB	OBJECT IDENTIFIER ::= { specMods 15 }
ennPSFBP	OBJECT IDENTIFIER ::= { specMods 16 }
ennMSTELCO	OBJECT IDENTIFIER ::= { specMods 17 }
ennPSTELCO	OBJECT IDENTIFIER ::= { specMods 18 }
tnnMSRJ45S	OBJECT IDENTIFIER ::= { specMods 19 }
tnnMSFIB	OBJECT IDENTIFIER ::= { specMods 20 }
ennMSTS		OBJECT IDENTIFIER ::= { specMods 21 }
ennMSFOIRL	OBJECT IDENTIFIER ::= { specMods 22 }
cnnNSRCTL	OBJECT IDENTIFIER ::= { specMods 23 }
ennMSFB		OBJECT IDENTIFIER ::= { specMods 24 }
fnnMSMGT	OBJECT IDENTIFIER ::= { specMods 25 }
fnnMSFBMIC	OBJECT IDENTIFIER ::= { specMods 26 }
fnnMSST OBJECT IDENTIFIER ::= { specMods 27 }
fnnMSDB9	OBJECT IDENTIFIER ::= { specMods 28 }
ennCSTELCO	OBJECT IDENTIFIER ::= { specMods 29 }
tnnPSBRG	OBJECT IDENTIFIER ::= { specMods 30 }
ee06PSBRG	OBJECT IDENTIFIER ::= { specMods 31 }
tnnMSMGT	OBJECT IDENTIFIER ::= { specMods 32 }
cnnNSHCTL	OBJECT IDENTIFIER ::= { specMods 33 }

--
-- Ethernet Carrier Module
-- Packaged as part of the EC-DMM blade (carrier with management option).
--
eC	OBJECT IDENTIFIER ::= { specMods 35 }


--
-- Distributed Management Module (DMM)
-- Packaged as part of the EC-DMM blade (carrier with management option).
--
xDMM	OBJECT IDENTIFIER ::= { specMods 43 } -- Module may be
							-- EC-DMM (ethernet

eMAC	  OBJECT IDENTIFIER ::= { specMods 45 } -- Ethernet MAC Module
e10PSFB		OBJECT IDENTIFIER ::= { specMods 46 }
e24PS6		OBJECT IDENTIFIER ::= { specMods 47 }
ennMSSTELCO	OBJECT IDENTIFIER ::= { specMods 48 }
ocRCTL8000	OBJECT IDENTIFIER ::= { specMods 50 }

cnnNSRCLS	OBJECT IDENTIFIER ::= { specMods 51 }



tnnMSEC		OBJECT IDENTIFIER ::= { specMods 62 }
ol52nnMXXX	OBJECT IDENTIFIER ::= { specMods 63 }
ol51nnMXXX	OBJECT IDENTIFIER ::= { specMods 64 }


tnnMSTDDI	OBJECT IDENTIFIER ::= { specMods 65 }



ol5101MRMON	OBJECT IDENTIFIER ::= { specMods 68 }



--
-- Networking groups
--

net		OBJECT IDENTIFIER ::= { nets 1 }
enet		OBJECT IDENTIFIER ::= { nets 2 }
trnet	OBJECT IDENTIFIER ::= { nets 3 }
fddinet		OBJECT IDENTIFIER ::= { nets 4 }



--
-- Threshold group
--

thresh  OBJECT IDENTIFIER ::= { alarm 1 }

threshControl	OBJECT IDENTIFIER ::= { thresh 1 }








-- The gen Group
--
-- Implementation of the gen group is mandatory for all agent products.
--
-- The gen Group is used by all agent products.  It provides
-- objects that identify what the product is and who is managing it.
--


genProduct OBJECT-TYPE
	SYNTAX INTEGER {
		product-E01MS-MGT(1),	-- EMM
		product-EE02PS-BRG(2),  -- EBM

		product-F01MS-MGT(5),	-- FMM
		product-T01MS-MGT(7)	-- TRMM

		,
		product-EC-DMM(12)	-- DMM
	}
	ACCESS read-only
	STATUS mandatory
	DESCRIPTION
		"The product type represented by this agent."
	::= { gen 1 }

genServiceDate OBJECT-TYPE
	SYNTAX DisplayString (SIZE(6))
	ACCESS read-only
	STATUS mandatory
	DESCRIPTION
		"The date that the product was last serviced in the
		format yymmdd.  If this date is unknown, the value of this
		object is '000000'."
	::= { gen 2 }

genNetman OBJECT-TYPE
	SYNTAX IpAddress
	ACCESS read-only
	STATUS mandatory
	DESCRIPTION
		"The IP (source) Address of the last authenticated SNMP PDU
		received by this entity before this request.  An IP Address
		of 00.00.00.00 represents the default value."
	::= { gen 3 }

genDiagnostics OBJECT-TYPE
	SYNTAX INTEGER {
		passed(1),
		failed(2)
	}
	ACCESS read-only
	STATUS mandatory
	DESCRIPTION
		"The result of this product's diagnostic test(s).  If
		any test fails, this will have the failed(2) value.
		Note, many products do not operate after a diagnostic
		failure.  In this case, no SNMP communication would
		be available."
	::= { gen 4 }

genSerial OBJECT-TYPE
	SYNTAX DisplayString (SIZE(1..128))
	ACCESS read-only
	STATUS mandatory
	DESCRIPTION
		"The serial number of this product."
	::= { gen 5 }

genID OBJECT-TYPE
	SYNTAX INTEGER
	ACCESS read-write
	STATUS mandatory
	DESCRIPTION
		"A unique ID used for grouping disparate agents together.
		For example, a concentrator may contain multiple agents.
		This ID is could be assigned by the management station
		to identify all of these agents as being contained in the
		same concentrator."
	::= { gen 6 }

genVers OBJECT-TYPE
	SYNTAX DisplayString (SIZE(0..80))
	ACCESS read-only
	STATUS mandatory
	DESCRIPTION
		"The version identifier(s) for this agent."
	::= { gen 7 }

genAuthFailureAddr OBJECT-TYPE
	SYNTAX IpAddress
	ACCESS read-only
	STATUS mandatory
	DESCRIPTION
		"The source IP Address of the last SNMP request that caused
		an authentication failure trap to be generated. This
		object is also included in the SNMP authenticationFailure
		trap."
	::= { gen 8 }

genTimeLastChanged OBJECT-TYPE
	SYNTAX TimeTicks
	ACCESS read-only
	STATUS mandatory
	DESCRIPTION
		"A snapshot of sysUpTime when the last trap was generated.
		This attribute can be used to save polling by a management
		station.  If there have been no traps generated since the last
		poll, there is no need for the station to poll again."
	::= { gen 9 }


-- The echo Group
--
-- Implementation of the echo group is mandatory for all agent
-- products.
--
-- The echo Group is used by a station to initiate a Ping from
-- this agent to the address denoted by echoAddr.  When all of
-- the pings are sent, the agent issues a ping trap (enterprise specific)
-- reporting the total number of responses received at that time.
--
-- To ping another host, you must minimally set the echoAddr to the
-- host that you want to ping and echoStart to startEcho(2).  The
-- other objects let you change the characteristic of the Ping packets.
-- Note that only one Ping can be processed at a time.
--

echoStart OBJECT-TYPE
	SYNTAX INTEGER {
		noEcho(1),
		startEcho(2)
		}
	ACCESS read-write
	STATUS mandatory
	DESCRIPTION
		"Setting echoStart to startEcho(2) causes the device
		to begin an ICMP echo sequence using the parameters
		indicated by the rest of the echo group."
	::= { echo 1 }

echoAddr OBJECT-TYPE
	SYNTAX IpAddress
	ACCESS read-write
	STATUS mandatory
	DESCRIPTION
		"The IP Address to which the device will ping.  This object can
	only be set to valid unicast class A, class B, or class C addresses. The
	default IP Address is loopback (127.0.0.1)."
	::= { echo 2 }

echoPattern OBJECT-TYPE
	SYNTAX INTEGER {
		zeroes(1),
		ones(2),
		mixed(3)
		}
	ACCESS read-write
	STATUS mandatory
	DESCRIPTION
		"The actual pattern to be contained in the ICMP echo packet."
	::= { echo 3 }


echoNumber OBJECT-TYPE
	SYNTAX INTEGER (1..255)
	ACCESS read-write
	STATUS mandatory
	DESCRIPTION
		"The number of ICMP echo packets (pings) to send."
	::= { echo 4 }


echoSize OBJECT-TYPE
	SYNTAX INTEGER (64..1500)
	ACCESS read-write
	STATUS mandatory
	DESCRIPTION
		"The size of the ICMP echo packet (ping) to send when
		echoStart is set. The valid range is between 64 and
		1500 octets."
	::= { echo 5 }

echoResponseCounts OBJECT-TYPE
	SYNTAX Counter
	ACCESS read-only
	STATUS mandatory
	DESCRIPTION
		"The count of ICMP echo response packets received since
		the last PING was initiated. "
	::= { echo 6 }



-- The Concentrator Groups:
--
-- The following groups are specific to the Concentrator product family.
--

-- The agents Group:

-- This group is mandatory for all agents that exist in the concentrator.
--
-- The master management module(s) indicate all of the other SNMP agents
-- present in the concentrator.  The agents group is also used
-- by each agent to indicate his own agent status, whether master or not.
--

agentsMySlot OBJECT-TYPE
	SYNTAX INTEGER
	ACCESS read-only
	STATUS mandatory
	DESCRIPTION
		"The slot id of this agent."
	::= { agents 1 }

agentsMasterReset OBJECT-TYPE
	SYNTAX  INTEGER {
		noReset(1),
		reset(2)
		}
	ACCESS read-write
	STATUS mandatory
	DESCRIPTION
		"Resetting mastership causes a new mastership election to
		occur. The agent with the highest mastership priority will
		become the new master.  If there is more than one agent
		with the highest priority, the selection between
		those agents will be arbritrary."
	::= { agents 2 }

agentsTable OBJECT-TYPE
	SYNTAX  SEQUENCE OF AgentsEntry
	ACCESS  not-accessible
	STATUS  mandatory
	DESCRIPTION
		"A table of agents in the concentrator as seen by
		this agent.  A master will see all the agents; a slave
		will only see itself."
	::= { agents 3 }

agentsEntry OBJECT-TYPE
	SYNTAX  AgentsEntry
	ACCESS  not-accessible
	STATUS  mandatory
	DESCRIPTION
		"A profile of an agent within the concentrator."
	INDEX	{ agentsSlotIndex }
	::= { agentsTable 1 }

AgentsEntry ::=
	SEQUENCE {
		agentsSlotIndex
			INTEGER,
		agentsStationAddr
			OCTET STRING,
		agentsIpAddress
			IpAddress,
		agentsMasterStatus
			INTEGER,
		agentsMasterPriority
			INTEGER,
		ocAgentsSubSlot
			INTEGER
		}

agentsSlotIndex OBJECT-TYPE
	SYNTAX  INTEGER
	ACCESS  read-only
	STATUS  mandatory
	DESCRIPTION
		"The slot number that identifies the referenced agent."
	::= { agentsEntry 1 }

agentsStationAddr OBJECT-TYPE
	SYNTAX  OCTET STRING (SIZE(6))
	ACCESS  read-only
	STATUS  mandatory
	DESCRIPTION
		"The unique identifier for this agent.  Often this
		is the value of ifPhysAddress for the first interface."
	::= { agentsEntry 2 }

agentsIpAddress OBJECT-TYPE
	SYNTAX  IpAddress
	ACCESS  read-only
	STATUS  mandatory
	DESCRIPTION
		"An IP Address that can be used to communicate to
		this agent.  Note, this object's value may change
		as the agent switches to different sub-networks."
	::= { agentsEntry 3 }

agentsMasterStatus OBJECT-TYPE
	SYNTAX INTEGER {
		master(1),
		non-master(2), -- slave
		electing(3)
		}
	ACCESS read-only
	STATUS mandatory
	DESCRIPTION
		"The mastership status of this agent."
	::= { agentsEntry 4 }

agentsMasterPriority OBJECT-TYPE
	SYNTAX INTEGER {
		one(1),		-- lowest
		two(2),
		three(3),
		four(4),
		five(5),
		six(6),
		seven(7),
		eight(8),
		nine(9),
		ten(10),	-- highest
		never(11)
		}
	ACCESS read-write
	STATUS mandatory
	DESCRIPTION
		"The mastership priority of this agent.  Ten is the
		highest and one is the lowest.  Never means will not
		be able become master.  Some agents do not have the
		capability to become master (the etherent to ethernet bridge,
		e.g.) and setting those agents to a value other than
		never(11) will generate an invalid value error.  Priority is
		only used when an election occurs.  Mastership is not
		pre-emptive; use the reset mastership command
		(agentsMasterReset)."
	::= { agentsEntry 5 }

ocAgentsSubSlot OBJECT-TYPE
	SYNTAX INTEGER
	ACCESS read-only
	STATUS mandatory
	DESCRIPTION
		"The subslot index for this agent.  For agents not located
		in the IBM 8260 system, this object will always
		return 1 for this object value."
	::= { agentsEntry 6 }


-- The conc Group:

-- This group is mandatory for all devices that are acting as a concentrator
-- master.
--
-- The conc group contains information and control relative to
-- the concentrator.
--

concType OBJECT-TYPE
	SYNTAX INTEGER {
		hub-seventeen-slot(1),
		hub-six-slot(2),
		hub-six-slot-ft(3),		-- 6 slot with flag board
		hub-six-slot-hc(4),	-- 6-slot with hidden controller
		hub-six-slot-ft-hc(5),  -- 6-slot with both
		hub8260-seventeen-slot-a(6)	-- 17 slot with ring backplane


		,
		hub-load-sharing(9)	-- 17 slot load sharing hub


	}
	ACCESS read-only
	STATUS mandatory
	DESCRIPTION
		"This object identifies the type of concentrator represented
		by this agent."
	::= { conc 1 }


concReset OBJECT-TYPE
	SYNTAX INTEGER {
		noReset(1),
		reset(2)
		}
	ACCESS read-write
	STATUS mandatory
	DESCRIPTION
		"Setting this value to reset(2) causes this concentrator to
		reset. "
	::= { conc 2 }


concNumSlots OBJECT-TYPE
	SYNTAX INTEGER
	ACCESS read-only
	STATUS mandatory
	DESCRIPTION
		"The number of slots in this concentrator.  Note, that
		if a hidden controller is present, the number of slots
		is one more than the number of payload slots (six-slot-hc
		will report 7 slots, for example). The hidden controller
		does not actually occupy a main slot in the 6-slot
		concentrator, but it will report itself as slot 7."
	::= { conc 3 }

concProfile OBJECT-TYPE
	SYNTAX OCTET STRING (SIZE(1..3))
	ACCESS read-only
	STATUS mandatory
	DESCRIPTION
		"A bit string where the least significant bit corresponds to
		slot 1.  A '1' in the bit indicates that a module is present
		in that slot.  The number of octets provided is based on
		the concNumSlots value divided by 8.  Any extra bits
		(for example, bits 18-24 for 17 slots) are meaningless.

		For example, the string 0x01 0xFF 0xFF would represent
		a full 17 slot concentrator."
	::= { conc 4 }


-- The env Group

-- This group represents the concentrator's environment.  It is available
-- from agents that are acting as a concentrator master.

envTempStatus OBJECT-TYPE
	SYNTAX INTEGER {
		okay(1),
		extremeTemp(2),
		warning(3)
		}
	ACCESS read-only
	STATUS mandatory
	DESCRIPTION
		"The overall temperature status for this concentrator.
		This object's value is an aggregate of all the temperature
		probes in the concentrator, such that, when at least one probe
		reports extreme temperature, this object will have the value
		extremeTemp(2).  This object will have the value warning(3)
		prior to reporting the value extremeTemp(2) as a means of
		warning of a possible hub overheat condition."
    ::= { env 1 }

envPSCapacity OBJECT-TYPE
	SYNTAX INTEGER
	ACCESS read-only
	STATUS mandatory
	DESCRIPTION
		"The total capacity of power supplies for this concentrator."
	::= { env 2 }

envPSTable OBJECT-TYPE
	SYNTAX SEQUENCE OF EnvPSEntry
	ACCESS not-accessible
	STATUS mandatory
	DESCRIPTION
		"A table that contains information about each potential
		power supply in the concentrator."
	::= { env 3 }


envPSEntry OBJECT-TYPE
	SYNTAX EnvPSEntry
	ACCESS not-accessible
	STATUS mandatory
	DESCRIPTION
		"A list of information for each power supply in the
		concentrator."
	INDEX { envPSIndex }
	::= { envPSTable 1 }

EnvPSEntry ::=
	SEQUENCE {
		envPSIndex
			INTEGER,
		envPSAdminState
			INTEGER,
		envPSOperStatus
			INTEGER
		}

envPSIndex OBJECT-TYPE
	SYNTAX INTEGER
	ACCESS read-only
	STATUS mandatory
	DESCRIPTION
		"Identifies the power supply for which this entry contains
		power supply information.  For systems with the
		primary and backup power supply (as opposed to
		the N+1 design), index 1 refers to the primary,
		and index 2 refers to the backup. "
	::= { envPSEntry 1 }

envPSAdminState OBJECT-TYPE
	SYNTAX INTEGER {
		activate(1),
		standby(2)
		}
	ACCESS read-write
	STATUS mandatory
	DESCRIPTION
		"The current desired state of the power supply.  A power
		supply in standby does not provide power to the concentrator.
		Note, in a Load Sharing Hub, this object is read only."
	::= { envPSEntry 2 }

envPSOperStatus OBJECT-TYPE
	SYNTAX INTEGER {
		active(1),
		standby(2),
		faulty(3),
		not-installed(4)
		}
	ACCESS read-only
	STATUS mandatory
	DESCRIPTION
		"The current operational state of the power supply.  A power
		supply in standby does not provide power to the concentrator."
	::= { envPSEntry 3 }

envFanStatus OBJECT-TYPE
	SYNTAX INTEGER {
		okay(1),
		faulty(2),
		not-installed(4),
		unknown(5)
		}
	ACCESS read-only
	STATUS mandatory
	DESCRIPTION
		"The overall status of the fan(s).  When fan operational
		status is known, this object's value is an aggregate of
		all fan status in the concentrator such that, when at
		least one fan unit is faulty, this object will have the
		value faulty(2)."
	::= { env 4 }


envTable OBJECT-TYPE
	SYNTAX SEQUENCE OF EnvEntry
	ACCESS not-accessible
	STATUS mandatory
	DESCRIPTION
		"A table that contains information about the concentrator
		environment."
	::= { env 5 }

envEntry OBJECT-TYPE
	SYNTAX EnvEntry
	ACCESS not-accessible
	STATUS mandatory
	DESCRIPTION
		"A list of information for each monitored component in this
		concentrator."
	INDEX { envType }
	::= { envTable 1 }

EnvEntry ::=
	SEQUENCE {
		envType
			INTEGER,
		envStatus
			INTEGER
		}

envType OBJECT-TYPE
	SYNTAX INTEGER {
		ls-pdb(1)		  --- Online load-sharing hub PDB
		}
	ACCESS read-only
	STATUS mandatory
	DESCRIPTION
		"The type of hardware component monitored in this
		concentrator."
	::= { envEntry 1 }

envStatus OBJECT-TYPE
	SYNTAX INTEGER {
		okay(1),
		faulty(2)
		}
	ACCESS read-only
	STATUS mandatory
	DESCRIPTION
		"The status of the monitored hardware component."
	::= { envEntry 2 }


-- The modules group

-- This group represents the information as seen by what is currently known
-- as the concentrator master.  If the module is not a master, this group
-- is not represented.  These tables have dynamic instances, that is,
-- if the module does not exist in the concentrator, the tables are empty.
-- No excess information is presented.
--
-- If the agent is an IBM 8260 management module, the modules that exist
-- in subslot 1 (that is, the motherboard) will have an instance in the
-- modTable
--

modTable	 OBJECT-TYPE
	SYNTAX SEQUENCE OF ModEntry
	ACCESS not-accessible
	STATUS mandatory
	DESCRIPTION
		"A table that contains generic information about every
		module that is present within the concentrator.
		If the concentrator is the IBM 8260 Hub, then only the
		motherboard is present in this table."
	::= { modules 1 }

modEntry OBJECT-TYPE
	SYNTAX ModEntry
	ACCESS not-accessible
	STATUS mandatory
	DESCRIPTION
		"A list of information for each module in the concentrator.
		If the concentrator is the IBM 8260 Hub, then only the
		motherboard is present in this table."
	INDEX { modSlotIndex }
	::= { modTable 1 }

ModEntry ::=
	SEQUENCE {
		modSlotIndex
			INTEGER,
		modType
			INTEGER,
		modClass
			INTEGER,
		modDescr
			DisplayString,
		modVersion
			DisplayString,
		modVendor
			INTEGER,
		modResetModule
			INTEGER,
		modConfigToDips
			INTEGER,
		modConfigured
			INTEGER,
		modNetwork
			INTEGER,
		modNetworkType
			INTEGER,
		modStatus
			INTEGER,
		modNumPorts
			INTEGER,
		modNumTrunks
			INTEGER

		}

modSlotIndex OBJECT-TYPE
	SYNTAX INTEGER
	ACCESS read-only
	STATUS mandatory
	DESCRIPTION
		"The unique slot number of this module.  Its value ranges
		between 1 and concNumSlots and remains constant at
		least from one re-initialization of the entity's network
		management system to the next re-initialization."
	::= { modEntry 1 }

modType OBJECT-TYPE
	SYNTAX INTEGER {
		module-unmanageable(1), -- not manageable
		module-unknown(2),	-- only generically manageable
		module-cnnNS-CTL(3),	-- Controller
		module-ennMS-MGT(4),	-- Ethernet Management
		module-ennMS-FIB(5),	-- Ethernet Fiber
		module-ennMS-UTP(6),	-- Ethernet 10BASE-T
		module-ennMS-RJ45S(7),  -- Ethernet 10BASE-T
		module-ennMS-BNC(8),	-- Ethernet BNC
		module-eennPS-BRG(9),	-- EBM
		module-esnnPS-RTR(10),  -- Cisco Serial
		module-eennPS-RTR(11),  -- Cisco Ethernet
		module-ennPS-AUIF(12),  -- Ethernet AUI Female
		module-ennPS-AUIM(13),  -- Ethernet AUI Male
		module-t08MS-RJ45S(14), -- Token Ring 8-port MAU module
		module-ennPS-FIB(15),	-- Ethernet Fiber port switching
		module-ennPS-FBP(16),	-- Ethernet 10BASE-F port switching
		module-ennMS-TELCO(17), -- Ethernet 10BASE-T
		module-ennPS-TELCO(18),  -- Ethernet 10BASE-T port switching
		module-tnnMS-RJ45S(19),    -- Token Ring Media Module
		module-tnnMS-FIB(20),	-- Token Ring FiberOptic Repeater
		module-ennMS-TS(21),	-- Ethernet Terminal Server
		module-ennMS-FOIRL(22), -- Ethernet FOIRL
		module-cnnNS-RCTL(23),  -- Redundant Controller
		module-ennPS-FB(24),	-- Ethernet 10BASE-F
		module-fnnMS-MGT(25),	-- FDDI managment module (FMM)
		module-fnnMS-FBMIC(26), -- FDDI media w/ fiber ANSI MIC conn.
		module-fnnMS-ST(27), -- FDDI media w/ fiber ST conn.
		module-fnnMS-DB9(28),	-- FDDI w/ shielded copper DB9 conn.
		module-ennCS-TELCO(29),		-- Ethernet 10BASE-T per-connector
		module-tnnPS-BRG(30),	-- Token Ring Bridge
		module-ee06PS-BRG(31),  -- Ethernet Interconnect Module
		module-tnnMS-MGT(32),	-- Token Ring Management
		module-cnnNS-HCTL(33),  -- Hidden Controller
		module-EC(35),  -- Ethernet Carrier Module

		module-DMM(43),   -- Distributed Management Module

		module-E-MAC(45),	-- Ethernet MAC monitor card
		module-E10PS-FB(46),	-- Ethernet 10-port per-port switchable fiber
		module-E24PS-6(47),	-- Ethernet 24-port per-port switching
		module-ennMS-TELCOS(48),  -- Ethernet 10BASE-T Security Module
		module-RCTL-8000(50),	-- IBM 8260 Ctlr (managed by IBM 8260 mgmt)

		module-CNNNS-RCLS(51),  -- Load Sharing Redundant Controller



		module-tnnMS-EC(62)	-- 3174 Establistment Controller

		,
		module-tnnMS-TDDI(65)	-- FDDI w/ copper RJ45 conn.




		}
	ACCESS read-only
	STATUS mandatory
	DESCRIPTION
		"The unique type identifier for this module.  This type
		is used to identify the branch in specMods (see below).

		module-unmanageable(1) means that only the following
		objects are valid for this module:

			modSlotIndex
			modClass
			modVersion
			modVendor
			modReset
			modConfigToDips
			modConfigured

		module-unknown(2) means that all the generic attributes
		are manageable, but there is no specMods branch
		for this module as viewed by this agent."
		::= { modEntry 2 }

modClass OBJECT-TYPE
	SYNTAX INTEGER {
		controller(1),
		mgmt(2),
		ethernet-media(3),
		ethernet-interconnect(4),
		ethernet-portswitching-media(5),
		token-ring-media(6),
		terminal-server(7),
		fddi-media(8),
		token-ring-mgmt(9),
		ethernet-connswitching-media(10),
		token-ring-interconnect(11),
		fddi-mgmt(12),
		hub8260-token-ring-media(13),
		ethernet-carrier(14),
		hub8260-oem-specials(15),

		hub8260-download(17),

		ethernet-media-extended(19),
		token-ring-mod-interconnect(20)


		}
	ACCESS read-only
	STATUS mandatory
	DESCRIPTION
		"The class of this module.  Generally speaking, this
		object indicates the kind of module.  Specifically,
		the class identifier specifies the internal representation
		of the module's managed information base."
	::= { modEntry 3 }

modDescr OBJECT-TYPE
	SYNTAX DisplayString (SIZE(1..128))
	ACCESS read-only
	STATUS mandatory
	DESCRIPTION
		"A textual string containing information about the module."
	::= { modEntry 4 }

modVersion OBJECT-TYPE
	SYNTAX DisplayString (SIZE(1..32))
	ACCESS read-only
	STATUS mandatory
	DESCRIPTION
		"The software version number of this module.  "
	::= { modEntry 5 }

modVendor OBJECT-TYPE
	SYNTAX INTEGER {
		chipcom(1),
		cisco(2),
		pilkington(3),
		datability(5),
		ibm(6),
		raycom(7),
		retix(8),
		intellicom(9)
		}
	ACCESS read-only
	STATUS mandatory
	DESCRIPTION
		"The actual manufacturer of this board."
	::= { modEntry 6 }

modResetModule OBJECT-TYPE
	SYNTAX INTEGER {
		noReset(1),
		reset(2)
		}
	ACCESS read-write
	STATUS mandatory
	DESCRIPTION
		"Setting this object to reset(2) causes this module to reset."
	::= { modEntry 7 }

modConfigToDips OBJECT-TYPE
	SYNTAX INTEGER {
		noConfigure(1),
		configure(2)
		}
	ACCESS read-write
	STATUS mandatory
	DESCRIPTION
		"Setting this object to configure(2) causes this module to
		configure based on the dip switch settings."
	::= { modEntry 8 }

modConfigured OBJECT-TYPE
	SYNTAX INTEGER {
		notConfigured(1),
		configured(2)
		}
	ACCESS read-only
	STATUS mandatory
	DESCRIPTION
		"This object indicates whether this module has already been
		configured.  An unconfigured module is configured to a safe
		state where the network is isolated and the ports are
		disabled."
	::= { modEntry 9 }


modNetwork OBJECT-TYPE
	SYNTAX INTEGER {
		other(1),
		isolated(2),
		port-switching(3),
		front-panel(5),
		ethernet-1(6),
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22),		-- isolated networks within the module
		isolated-3(23),
		isolated-4(24),
		isolated-5(25),
		isolated-6(26),
		isolated-7(27),
		isolated-8(28),
		isolated-9(29),
		isolated-10(30),
		isolated-11(31),
		ethernet-4(32),		-- Available in IBM 8260.
		ethernet-5(33),
		ethernet-6(34),
		ethernet-7(35),
		ethernet-8(36)

		}
	ACCESS read-write
	STATUS mandatory
	DESCRIPTION
		"The network that this module is attached to.  If the
		value is other(1) or port-switching(3), setting this object
		to a different value will generate the invalidData error.

		If the value is port-switching(3), manage the networks via
		the portNetwork object.

		The value per-connector(20) is returned if the managed
		module is a per-connector switchable and the connectors are on
		different networks.  The connector networks are managed
		by the objects defined in the specMods branch
		specified for this module.

		Modules and ports on the same network intercommunicate.
		Setting the module to isolated(2) (or other isolated values),
		removes this module from the backplane.

		Setting this module to a value that is not the same
		protocol type will return an invalidData error.

		Setting this module to a value that it does not support
		will return an invalidData error."
	::= { modEntry 10 }

modNetworkType OBJECT-TYPE
	SYNTAX INTEGER {
		other(1),	    -- other only
		port-switching(3),  -- use portNetwork
		ethernet(5),	    -- ethernet 1-3 or 1-8, isolated
		token-ring(6), -- token-ring 1-7, isolated,

		fddi(7),	    -- fddi 1-4, isolated
		serial(8)	    -- front or isolated only
		}
	ACCESS read-only
	STATUS mandatory
	DESCRIPTION
		"The network type of this module.  port-switching(3)
		means that the network type differs depending on the
		port (like the router module). The network type reflects
		the valid values for modNetwork."
	::= { modEntry 11 }

modStatus OBJECT-TYPE
	SYNTAX INTEGER {
		okay(1),
		fatalError(10),
		booting(20),
		partial-failure(21)
		}
	ACCESS read-only
	STATUS mandatory
	DESCRIPTION
		"The module's status."
	::= { modEntry 12 }

modNumPorts OBJECT-TYPE
	SYNTAX INTEGER
	ACCESS read-only
	STATUS mandatory
	DESCRIPTION
		"The number of ports on this module.  Note, ports may be
		physical ports like 10BASE-T ports, or logical, like
		the bridge module ports."
	::= { modEntry 13 }

modNumTrunks OBJECT-TYPE
	SYNTAX INTEGER
	ACCESS read-only
	STATUS mandatory
	DESCRIPTION
		"The number of trunks on this module.  Note, trunks
		are links that are, by definition, backbone connections.
		Examples of trunks are ring in and ring out ports for
		token ring, and the connections for rings to the backplane."
	::= { modEntry 14 }


--
-- Generic Port Table
--

portTable OBJECT-TYPE
	SYNTAX SEQUENCE OF PortEntry
	ACCESS not-accessible
	STATUS mandatory
	DESCRIPTION
		"A table that contains generic information about
		each port on each module present within the concentrator."
	::= { modules 2 }

portEntry OBJECT-TYPE
	SYNTAX PortEntry
	ACCESS not-accessible
	STATUS mandatory
	DESCRIPTION
		"A list of information about each port in the
		concentrator."
	INDEX { portSlotIndex, portIndex }
	::= { portTable 1}

PortEntry ::=
	SEQUENCE {
		portSlotIndex
			INTEGER,
		portIndex
			INTEGER,
		portType
			INTEGER,
		portConnector
			INTEGER,
		portStatus
			INTEGER,
		portAdminState
			INTEGER,
		portNetwork
			INTEGER,
		portNetworkType
			INTEGER,
		portAlertFilter
			INTEGER
		}

portSlotIndex OBJECT-TYPE
	SYNTAX INTEGER
	ACCESS read-only
	STATUS mandatory
	DESCRIPTION
		"The slot number of this port's module."
	::= { portEntry 1 }

portIndex OBJECT-TYPE
	SYNTAX INTEGER
	ACCESS read-only
	STATUS mandatory
	DESCRIPTION
		"The port number of this port within this module."
	::= { portEntry 2 }

portType OBJECT-TYPE
	SYNTAX INTEGER {
		logical(1),	-- ebm's ports for example
		media(2),	-- normal ports
		virtual(5)	-- ets'  ports for example
		}
	ACCESS read-only
	STATUS mandatory
	DESCRIPTION
		"The type of port.  logical(1) is used to manage
		port resources that may not map directly to physical
		connections.  The EBM, for example, has two logical
		ports, although those two ports can be assigned to
		different combinations of four physical connections.
		media(2) refers to ports such as those on the 10BASE-T
		module. "
	::= { portEntry 3 }


portConnector OBJECT-TYPE
	SYNTAX INTEGER {
		backPlane(1),		-- connects directly to backplane
		bnc(2),			-- thinnet
		faui(3),		-- female aui
		maui(4),		-- male aui
		fiber(5),		-- fiber connector
		db-50(6),		-- serial port
		telco(7),		-- 50 pin connector
		rj45(8),		-- unshielded
		rj45S(9),		-- shielded
		db-9(10),		-- 9 pin connector
		virtual(11),		-- e.g. terminal server port
		fddi-lc(12),		-- low cost connector
		fddi-st(13),		-- ST type connector
		fddi-mic(14),		-- MIC connector
		db-25(15),		-- 25 pin d-shell connector
		ethernet-sma(17),	-- SMA fiber connector
		ethernet-fc(23),	-- FC fiber connector
		ethernet-st(24)		-- ST fiber connector
		}
	ACCESS read-only
	STATUS mandatory
	DESCRIPTION
		"The connector type of this port."
	::= { portEntry 4 }

portStatus OBJECT-TYPE
	SYNTAX INTEGER {
		okay(1),
		linkFailure(2),
		jabber(3),
		remoteLinkFailure(4),
		remoteJabber(5),
		invalidData(6),
		lowLight(7),
		fifoOverrun(8),
		fifoUnderrun(9),
		fatalError(10),
		partition(11),
		mjlp(12),
		noCable(13),
		noSquelch(14),
		noPhantom(15),
		okay-standby(19),
		off(22),
		connecting(23),
		backup-link(24),
		security-breach(25),
		unknownStatus(26),
		beacon(27),
		wireFault(28),
		macRemoved(29),
		notInserted(30),
		speedMismatch(31),
		attach3174Unknown(32),
		attach3174To8-3299(33),
		attach3174To32-3299(34),
		attach3174ToDirect(35),
		attach3174Unavailable(36),
		transientError(37)


		}
	ACCESS read-only
	STATUS mandatory
	DESCRIPTION
		"The status of this port."
	::= { portEntry 5 }

portAdminState OBJECT-TYPE
	SYNTAX INTEGER {
		enabled(1),	      -- only valid value for class 2&4 modules
		disabled(2),
		redundant-primary(3), -- use specMods to set
		redundant-backup(4),  -- redundancy buddys
		redundant-rfs(5),     -- used by FOIRL only
		local(6),	      -- terminal server only
		remote(7),	      -- terminal server only
		remote-diagnostics(8),
		unknown(9)
		}
	ACCESS read-write
	STATUS mandatory
	DESCRIPTION
		"The desired state of this port.  Setting a port to be
		redundant-primary(3) or redundant-backup requires that the
		buddy slot and buddy port also be set to valid values
		(see appropriate specMods objects).  If the
		values associated with the redundant buddys
		are not valid, a genError will be returned.  If the port
		is already redundant, an invalid set may result in both
		ports being disabled."
	::= { portEntry 6 }

portNetwork OBJECT-TYPE
	SYNTAX INTEGER {
		other(1),
		isolated(2),
		per-module(4),
		front-panel(5),
		ethernet-1(6),
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22),		-- isolated networks within the module
		isolated-3(23),
		isolated-4(24),
		isolated-5(25),
		isolated-6(26),
		isolated-7(27),
		isolated-8(28),
		isolated-9(29),
		isolated-10(30),
		isolated-11(31),
		ethernet-4(32),
		ethernet-5(33),
		ethernet-6(34),
		ethernet-7(35),
		ethernet-8(36)

		}
	ACCESS read-write
	STATUS mandatory
	DESCRIPTION
		"The network that this port is attached to.

		If the value of portNetwork is per-module(4),
		then use the modNetwork to manage this port.
		Setting portNetwork to a different value in this
		case will generate the invalidData error.

		Setting this port to a value that is not the same protocol
		type will return invalidData error.  front-panel(5) is used for
		modules that have a logical port and a physical front
		connection. An example of this is the Eth2Eth Bridge module.

		Setting this port to a value that it does not support will
		generate an invalidData error."
	::= { portEntry 7 }

portNetworkType OBJECT-TYPE
	SYNTAX INTEGER {
		other(1),	-- other only
		ethernet(5),	-- ethernet 1-3, isolated

		fddi(7),	-- fddi 1-4, isolated
		serial(8)	-- front or isolated only
		}
	ACCESS read-only
	STATUS mandatory
	DESCRIPTION
		"The network type of this port.  The type reflects the
		valid values for portNetwork. "
	::= { portEntry 8 }

portAlertFilter OBJECT-TYPE
	SYNTAX INTEGER {
		enable(1),
		disable(2),
		other(3)
		}
	ACCESS read-write
	STATUS mandatory
	DESCRIPTION
		"Enabling this object for a port will allow the
		generation of port up (or port down) traps for port status
		transitions caused by end stations powering up (or down).
		Disabling this object will suppress the generation of port up
		(or port down) traps for a port.

		Note that this object is used in the trap generation decision
		only if alertMode, an object in alertTable, is set
		to filter(3).

		Some ports, such as integrated bridge or router ports
		do not support this feature. A getRequest on one of these
		types of  ports will return a value of other(3), and a
		setRequest to enable(1) or disable(2) will return
		the invalidData object. "
	::= { portEntry 9 }

--
-- Trunk Table
--

trunkTable OBJECT-TYPE
	SYNTAX SEQUENCE OF TrunkEntry
	ACCESS not-accessible
	STATUS mandatory
	DESCRIPTION
		"A table that contains generic information about
		each trunk on each module present within the concentrator."
	::= { modules 3 }

trunkEntry OBJECT-TYPE
	SYNTAX TrunkEntry
	ACCESS not-accessible
	STATUS mandatory
	DESCRIPTION
		"A list of information about each trunk in the
		concentrator."
	INDEX { trunkSlotIndex, trunkIndex }
	::= { trunkTable 1}

TrunkEntry ::=
	SEQUENCE {
		trunkSlotIndex
			INTEGER,
		trunkIndex
			INTEGER,
		trunkType
			INTEGER,
		trunkConnector
			INTEGER,
		trunkStatus
			INTEGER,
		trunkAdminState
			INTEGER,
		trunkWrapState
			INTEGER,
		trunkNeighbor
			INTEGER

		}

trunkSlotIndex OBJECT-TYPE
	SYNTAX INTEGER
	ACCESS read-only
	STATUS mandatory
	DESCRIPTION
		"The slot number of this trunk's module."
	::= { trunkEntry 1 }

trunkIndex OBJECT-TYPE
	SYNTAX INTEGER
	ACCESS read-only
	STATUS mandatory
	DESCRIPTION
		"The trunk number of this trunk."
	::= { trunkEntry 2 }

trunkType OBJECT-TYPE
	SYNTAX INTEGER {
		other(1),
		ringIn(3),	-- ring access trunks
		ringOut(4),
		backplaneIn(6), -- backplane access
		backplaneOut(7)
		}
	ACCESS read-only
	STATUS mandatory
	DESCRIPTION
		"The type of trunk. ringIn(3) and ringOut(4) refer to special
		trunks on the token ring protocol type modules."
	::= { trunkEntry 3 }


trunkConnector OBJECT-TYPE
	SYNTAX INTEGER {
		backplane(1),
		fiber(5),	--
		rj45S(9)	-- shielded
		}
	ACCESS read-only
	STATUS mandatory
	DESCRIPTION
		"The connector type of this trunk."
	::= { trunkEntry 4 }

trunkStatus OBJECT-TYPE
	SYNTAX INTEGER {
		okay(1),
		linkFailure(2),
		fatalError(10),
		noCable(13),
		noSquelch(14),
		lostLock(16),
		upstreamNeighborLost(17),
		invalidConfig(18),

		beacon(27),
		wireFault(28)

		}
	ACCESS read-only
	STATUS mandatory
	DESCRIPTION
		"The status of this trunk."
	::= { trunkEntry 5 }

trunkAdminState OBJECT-TYPE
	SYNTAX INTEGER {
		enabled(1),
		disabled(2)

		}
	ACCESS read-write
	STATUS mandatory
	DESCRIPTION
		"The desired state of this trunk.  Enabling a trunk
		allows the trunk to pass network traffic.  This
		object may be used to configure fiber trunk
		redundancy.  Setting a trunk to be redundant-primary(3)
		or redundant-backup(4) requires that the buddy slot
		be previously set to a valid value (see appropriate
		specMods objects).  If fiber trunk redundancy is
		already configured, setting this object to a
		redundant state will remove the previous configuration."
	::= { trunkEntry 6 }

trunkWrapState OBJECT-TYPE
	SYNTAX INTEGER {
		wrapped(1),
		unwrapped(2)
		}
	ACCESS read-only
	STATUS mandatory
	DESCRIPTION
		"The wrap state of this trunk.  A trunk can wrap in
		response to a network event such as a break in
		the cable."
	::= { trunkEntry 7 }

trunkNeighbor OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		external(256)
		}
	ACCESS read-only
	STATUS mandatory
	DESCRIPTION
		"The upstream or downstream neighbor of the trunk."
	::= { trunkEntry 8 }



-- specMods Group
--
-- This group contains the module and port tables specific to the
-- particular module.  Each module is indexed by the modType value.
-- For more information, please refer to the MIB information supplied
-- with each module.

-- specMods Group takes the following object identifier format:
--
-- specMods.<type>.<level>.1.<object>.<instance>
--
-- where :
--	<type> ::= the unique number identifying the type of this module
--			see modType above.
--	<level> ::= module table (1) ||
--		    port table (2)   ||
--		    trunk  (3)       ||
--		    submodule table (6)
--	1	::= branch for entry, i.e. module entry or port entry
--	<object>::= the object ID as indicated in the MIB documentation for
--			this type module.
--	<instance> ::=
--			<slot> for module level ||
--			<slot>.<port> for port level ||
--			<slot>.<trunk> for trunk level ||
--			<slot>.<subslot> for submodule level
--
--
--	The lexicographical ordering for this group is:
--
--	1. To walk through all of the instances associated
--		particular module type.  That is, the group
--		walks through a module type - all slots, before
--		walking to the next module type.  For example, if
--		module type A is in slot 1 & 5, and module type B
--		is in slot 3 (where A < B), then a tree walk would
--		yield A.1, A.3, and then B.3.
--
--	2. To walk through all of the resources of a particular module
--		before walking to the next module.  All ports and trunks
--		of a module are instantiated in the tree before the
--		the next module is instiated.
--
--	3. IBM 8260 modules do not return a module level table, only
--		a submodule level table.
--

--
-- Hub Controller Module
--

cnnNSCTLModTable OBJECT-TYPE
	SYNTAX SEQUENCE OF CnnNSCTLModEntry
	ACCESS not-accessible
	STATUS mandatory
	DESCRIPTION
		"A table that contains information about each cnnNS-CTL
		in the concentrator.  Note, current architecture will
		limit the number of instances to one per concentrator."
	::= { cnnNSCTL 1 }

cnnNSCTLModEntry OBJECT-TYPE
	SYNTAX CnnNSCTLModEntry
	ACCESS not-accessible
	STATUS mandatory
	DESCRIPTION
		"A list of information for each cnnNS-CTL module
		in the concentrator."
	INDEX { cnnNSCTLModSlotIndex }
	::= { cnnNSCTLModTable 1 }

CnnNSCTLModEntry ::=
	SEQUENCE {
		cnnNSCTLModSlotIndex
			INTEGER,
		cnnNSCTLModTempStatus
			INTEGER
		}

cnnNSCTLModSlotIndex OBJECT-TYPE
	SYNTAX INTEGER
	ACCESS read-only
	STATUS mandatory
	DESCRIPTION
		"The slot number for this module."
	::= { cnnNSCTLModEntry 1 }

cnnNSCTLModTempStatus OBJECT-TYPE
	SYNTAX INTEGER {
		okay(1),
		extremeTemp(2)
		}
	ACCESS read-only
	STATUS mandatory
	DESCRIPTION
		"The temperature as detected by the probes on this module."
	::= { cnnNSCTLModEntry 2 }


--
-- Ethernet Management Module
--

ennMSMGTModTable OBJECT-TYPE
	SYNTAX SEQUENCE OF EnnMSMGTModEntry
	ACCESS not-accessible
	STATUS mandatory
	DESCRIPTION
		"A table that contains module information about each
		EMM module in the concentrator."
	::= { ennMSMGT 1 }

ennMSMGTModEntry OBJECT-TYPE
	SYNTAX EnnMSMGTModEntry
	ACCESS not-accessible
	STATUS mandatory
	DESCRIPTION
		"A list of module information for a particular EMM module
		in the concentrator."
	INDEX { ennMSMGTModSlotIndex }
	::= { ennMSMGTModTable 1 }

EnnMSMGTModEntry ::=
	SEQUENCE {
		ennMSMGTModSlotIndex
			INTEGER,
		ennMSMGTModMasterPriority
			INTEGER,
		ennMSMGTModMasterStatus
			INTEGER,
		ennMSMGTModStationAddr
			OCTET STRING
		}

ennMSMGTModSlotIndex OBJECT-TYPE
	SYNTAX INTEGER
	ACCESS read-only
	STATUS mandatory
	DESCRIPTION
		"The slot number of this module."
	::= { ennMSMGTModEntry 1 }

ennMSMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent.  Ten is the
		highest and one is the lowest.  Priority is
		only used when an election occurs.  Mastership is not
		preemptive unless the reset mastership command is used."
	::= { ennMSMGTModEntry 2 }

ennMSMGTModMasterStatus OBJECT-TYPE
	SYNTAX INTEGER {
		master(1),
		non-master(2),
		electing(3)
		}
	ACCESS read-only
	STATUS mandatory
	DESCRIPTION
		"The mastership status of this agent."
	::= { ennMSMGTModEntry 3 }

ennMSMGTModStationAddr OBJECT-TYPE
	SYNTAX OCTET STRING (SIZE(6))
	ACCESS read-only
	STATUS mandatory
	DESCRIPTION
		"A 6 octet address that uniquely identifies this module.
		The station address is the mac address of port 1.  Note
		that EMMs before v3.0 will have 00-00-00-00-00-00 as their
		station address."
	::= { ennMSMGTModEntry 4 }

ennMSMGTPortTable OBJECT-TYPE
	SYNTAX SEQUENCE OF EnnMSMGTPortEntry
	ACCESS not-accessible
	STATUS mandatory
	DESCRIPTION
		"A table of information that contains port-specific
		information for each port on each ennMS-MGT module."
	::= { ennMSMGT 2 }

ennMSMGTPortEntry OBJECT-TYPE
	SYNTAX EnnMSMGTPortEntry
	ACCESS not-accessible
	STATUS mandatory
	DESCRIPTION
		"A list of information about a specific port on a
		ennMS-MGT module."
	INDEX { ennMSMGTPortSlotIndex, ennMSMGTPortIndex }
	::= { ennMSMGTPortTable 1 }

EnnMSMGTPortEntry ::=
	SEQUENCE {
		ennMSMGTPortSlotIndex
			INTEGER,
		ennMSMGTPortIndex
			INTEGER,
		ennMSMGTPortIpAddress
			IpAddress
		}

ennMSMGTPortSlotIndex OBJECT-TYPE
	SYNTAX INTEGER
	ACCESS read-only
	STATUS mandatory
	DESCRIPTION
		"The slot number of this port's module."
	::= { ennMSMGTPortEntry 1 }


ennMSMGTPortIndex OBJECT-TYPE
	SYNTAX INTEGER
	ACCESS read-only
	STATUS mandatory
	DESCRIPTION
		"The port number of this port."
	::= { ennMSMGTPortEntry 2 }


ennMSMGTPortIpAddress OBJECT-TYPE
	SYNTAX IpAddress
	ACCESS read-only
	STATUS mandatory
	DESCRIPTION
		"The IP Address associated with this port."
	::= { ennMSMGTPortEntry 3 }

--
-- Ethernet Synchronous Fiber Module
--


ennMSFIBModTable OBJECT-TYPE
	SYNTAX SEQUENCE OF EnnMSFIBModEntry
	ACCESS not-accessible
	STATUS mandatory
	DESCRIPTION
		"A table of module-specific information for each
		ennMS-FIB module in the concentrator."
	::= { ennMSFIB 1 }

ennMSFIBModEntry OBJECT-TYPE
	SYNTAX EnnMSFIBModEntry
	ACCESS not-accessible
	STATUS mandatory
	DESCRIPTION
		"A list of module-specific information associated
		with a particular ennMS-FIB module in the concentrator."
	INDEX { ennMSFIBModSlotIndex }
	::= { ennMSFIBModTable 1 }

EnnMSFIBModEntry ::=
	SEQUENCE {
		ennMSFIBModSlotIndex
			INTEGER,
		ennMSFIBModDipNetwork
			INTEGER,
		ennMSFIBModLLW
			INTEGER,
		ennMSFIBModDipLLW
			INTEGER
		}

ennMSFIBModSlotIndex OBJECT-TYPE
	SYNTAX INTEGER
	ACCESS read-only
	STATUS mandatory
	DESCRIPTION
		"The slot number of this module."
	::= { ennMSFIBModEntry 1 }

ennMSFIBModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSFIBModEntry 2 }

ennMSFIBModLLW OBJECT-TYPE
	SYNTAX INTEGER {
		enabled(1),
		disabled(2)
		}
	ACCESS read-write
	STATUS mandatory
	DESCRIPTION
		"The current state of this module's low light warning
		configuration.  Enabling this feature causes the module to
		check for low light and to issue a warning if low light is
		present.  Disabling low light has the advantage of faster
		redundancy switchover in the event of a port error."
	::= { ennMSFIBModEntry 3 }

ennMSFIBModDipLLW OBJECT-TYPE
	SYNTAX INTEGER {
		enabled(1),
		disabled(2)
		}
	ACCESS read-only
	STATUS mandatory
	DESCRIPTION
		"The low light warning configuration indicated by this module's
		dip switches."
	::= { ennMSFIBModEntry 4 }

ennMSFIBPortTable OBJECT-TYPE
	SYNTAX SEQUENCE OF EnnMSFIBPortEntry
	ACCESS not-accessible
	STATUS mandatory
	DESCRIPTION
		"A table of port-specific information for each port
		of each ennMS-FIB module."
	::= { ennMSFIB 2 }

ennMSFIBPortEntry OBJECT-TYPE
	SYNTAX EnnMSFIBPortEntry
	ACCESS not-accessible
	STATUS mandatory
	DESCRIPTION
		"A list of information about a specific port on a
		ennMS-FIB module."
	INDEX { ennMSFIBPortSlotIndex, ennMSFIBPortIndex }
	::= { ennMSFIBPortTable 1 }

EnnMSFIBPortEntry ::=
	SEQUENCE {
		ennMSFIBPortSlotIndex
			INTEGER,
		ennMSFIBPortIndex
			INTEGER,
		ennMSFIBPortAdminState
			INTEGER,
		ennMSFIBPortBuddySlot
			INTEGER,
		ennMSFIBPortBuddyPort
			INTEGER,
		ennMSFIBPortDipAdminState
			INTEGER
		}

	ennMSFIBPortSlotIndex OBJECT-TYPE
	SYNTAX INTEGER
	ACCESS read-only
	STATUS mandatory
	DESCRIPTION
		"The slot number of this port's module."
	::= { ennMSFIBPortEntry 1 }


ennMSFIBPortIndex OBJECT-TYPE
	SYNTAX INTEGER
	ACCESS read-only
	STATUS mandatory
	DESCRIPTION
		"The port number of this port."
	::= { ennMSFIBPortEntry 2 }


ennMSFIBPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennMSFIBPortEntry 3 }

ennMSFIBPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennMSFIBPortEntry 4 }

ennMSFIBPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennMSFIBPortEntry 5 }


ennMSFIBPortDipAdminState OBJECT-TYPE
	SYNTAX INTEGER {
		enabled(1),
		disabled(2),
		redundant-primary(3),
		redundant-backup(4)
		}
	ACCESS read-only
	STATUS mandatory
	DESCRIPTION
		"The state of this port as indicated by the port's dip
		switches."
	::= { ennMSFIBPortEntry 6 }

--
-- Ethernet 10BASE-T Module
--


ennMSUTPModTable OBJECT-TYPE
	SYNTAX SEQUENCE OF EnnMSUTPModEntry
	ACCESS not-accessible
	STATUS mandatory
	DESCRIPTION
		"A list of module-specific information associated
		with a particular ennMS-UTP module in the concentrator."
	::= { ennMSUTP 1 }

ennMSUTPModEntry OBJECT-TYPE
	SYNTAX EnnMSUTPModEntry
	ACCESS not-accessible
	STATUS mandatory
	DESCRIPTION
		"A module entry containing objects that describe the
		module level for that particular module."
	INDEX { ennMSUTPModSlotIndex }
	::= { ennMSUTPModTable 1 }

EnnMSUTPModEntry ::=
	SEQUENCE {
		ennMSUTPModSlotIndex
			INTEGER,
		ennMSUTPModDipNetwork
			INTEGER,
		ennMSUTPModCrossover
			INTEGER,
		ennMSUTPModDipCrossover
			INTEGER,
		ennMSUTPModFFL
			INTEGER,
		ennMSUTPModDipFFL
			INTEGER
		}

ennMSUTPModSlotIndex OBJECT-TYPE
	SYNTAX INTEGER
	ACCESS read-only
	STATUS mandatory
	DESCRIPTION
		"The slot number of this module."
	::= { ennMSUTPModEntry 1 }

ennMSUTPModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSUTPModEntry 2 }

ennMSUTPModCrossover OBJECT-TYPE
	SYNTAX INTEGER {
		crossed(1),
		uncrossed(2)
		}
	ACCESS read-write
	STATUS mandatory
	DESCRIPTION
		"The current state of this module's crossover
		configuration.  Setting this object to uncrossed(2)
		allows the last port to be used to connect to another
		repeater.  Often this feature is used to connect one 10BASE-T
		module to another."
	::= { ennMSUTPModEntry 3 }

ennMSUTPModDipCrossover OBJECT-TYPE
	SYNTAX INTEGER {
		crossed(1),
		uncrossed(2)
		}
	ACCESS read-only
	STATUS mandatory
	DESCRIPTION
		"The crossover configuration indicated by this module's
		dip switches."
	::= { ennMSUTPModEntry 4 }

ennMSUTPModFFL OBJECT-TYPE
	SYNTAX INTEGER {
		eight-bits(1),
		seven-bits(2)
		}
	ACCESS read-write
	STATUS mandatory
	DESCRIPTION
		"The number of bits to store in the repeater's fifo
		buffer.  See the module user's guide for more information."
	::= { ennMSUTPModEntry 5 }

ennMSUTPModDipFFL OBJECT-TYPE
	SYNTAX INTEGER {
		eight-bits(1),
		seven-bits(2)
		}
	ACCESS read-write
	STATUS mandatory
	DESCRIPTION
		"The fifo fill level as indicated by this module's dip
		switches."
	::= { ennMSUTPModEntry 6 }

ennMSUTPPortTable			 OBJECT-TYPE
	SYNTAX SEQUENCE OF EnnMSUTPPortEntry
	ACCESS not-accessible
	STATUS mandatory
	DESCRIPTION
		"A table of port-specific information for each port of
		this module type."
	::= { ennMSUTP 2 }

ennMSUTPPortEntry OBJECT-TYPE
	SYNTAX EnnMSUTPPortEntry
	ACCESS not-accessible
	STATUS mandatory
	DESCRIPTION
		"A port entry containing objects that describe this port."
	INDEX { ennMSUTPPortSlotIndex, ennMSUTPPortIndex }
	::= { ennMSUTPPortTable 1 }

EnnMSUTPPortEntry ::=
	SEQUENCE {
		ennMSUTPPortSlotIndex
			INTEGER,
		ennMSUTPPortIndex
			INTEGER,
		ennMSUTPPortAdminState
			INTEGER,
		ennMSUTPPortBuddySlot
			INTEGER,
		ennMSUTPPortBuddyPort
			INTEGER,
		ennMSUTPPortDipAdminState
			INTEGER,
		ennMSUTPPortLinkInteg
			INTEGER,
		ennMSUTPPortDipLinkInteg
			INTEGER,
		ennMSUTPPortSquelch
			INTEGER,
		ennMSUTPPortDipSquelch
			INTEGER
		}

	ennMSUTPPortSlotIndex OBJECT-TYPE
	SYNTAX INTEGER
	ACCESS read-only
	STATUS mandatory
	DESCRIPTION
		"The slot number of this port's module."
	::= { ennMSUTPPortEntry 1 }


ennMSUTPPortIndex OBJECT-TYPE
	SYNTAX INTEGER
	ACCESS read-only
	STATUS mandatory
	DESCRIPTION
		"The port number of this port."
	::= { ennMSUTPPortEntry 2 }

ennMSUTPPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennMSUTPPortEntry 3 }

ennMSUTPPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennMSUTPPortEntry 4 }

ennMSUTPPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennMSUTPPortEntry 5 }

ennMSUTPPortDipAdminState OBJECT-TYPE
	SYNTAX INTEGER {
		enabled(1),
		disabled(2)
		}
	ACCESS read-only
	STATUS mandatory
	DESCRIPTION
		"The state of this port as indicated by the port's dip
		switches."
	::= { ennMSUTPPortEntry 6 }

ennMSUTPPortLinkInteg OBJECT-TYPE
	SYNTAX INTEGER {
		enabled(1),
		disabled(2)
		}
	ACCESS read-write
	STATUS mandatory
	DESCRIPTION
		"The port's link integrity configuration.  Enabling
		link integrity configures the port to conform to
		the link integrity feature as specified by 10BASE-T."
	::= { ennMSUTPPortEntry 7 }

ennMSUTPPortDipLinkInteg OBJECT-TYPE
	SYNTAX INTEGER {
		enabled(1),
		disabled(2)
		}
	ACCESS read-only
	STATUS mandatory
	DESCRIPTION
		"The link integrity configuration as indicated by this
		port's dip switches."
	::= { ennMSUTPPortEntry 8 }

ennMSUTPPortSquelch	 OBJECT-TYPE
	SYNTAX INTEGER {
		normal(1),		-- high squelch
		low(2)
		}
	ACCESS read-write
	STATUS mandatory
	DESCRIPTION
		"The port's squelch configuration.  See the module's
		user's guide for more information."
	::= { ennMSUTPPortEntry 9 }

ennMSUTPPortDipSquelch   OBJECT-TYPE
	SYNTAX INTEGER {
		normal(1),		-- high squelch
		low(2)
		}
	ACCESS read-only
	STATUS mandatory
	DESCRIPTION
		"The port's squelch configuration as indicated by this
		port's dip switches."
	::= { ennMSUTPPortEntry 10 }


--
-- Ethernet 10BASE-T Module
--

ennMSRJ45SModTable OBJECT-TYPE
	SYNTAX SEQUENCE OF EnnMSRJ45SModEntry
	ACCESS not-accessible
	STATUS mandatory
	DESCRIPTION
		"A table of module-specific information for each
		ennMS-RJ45S module in the concentrator."
	::= { ennMSRJ45S 1 }

ennMSRJ45SModEntry OBJECT-TYPE
	SYNTAX EnnMSRJ45SModEntry
	ACCESS not-accessible
	STATUS mandatory
	DESCRIPTION
		"A list of module-specific information about a
		specific ennMS-RJ45S module in the concentrator."
	INDEX { ennMSRJ45SModSlotIndex }
	::= { ennMSRJ45SModTable 1 }

EnnMSRJ45SModEntry ::=
	SEQUENCE {
		ennMSRJ45SModSlotIndex
			INTEGER,
		ennMSRJ45SModDipNetwork
			INTEGER,
		ennMSRJ45SModCrossover
			INTEGER,
		ennMSRJ45SModDipCrossover
			INTEGER
		}

ennMSRJ45SModSlotIndex OBJECT-TYPE
	SYNTAX INTEGER
	ACCESS read-only
	STATUS mandatory
	DESCRIPTION
		"The slot number of this module."
	::= { ennMSRJ45SModEntry 1 }

ennMSRJ45SModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSRJ45SModEntry 2 }

ennMSRJ45SModCrossover OBJECT-TYPE
	SYNTAX INTEGER {
		crossed(1),
		uncrossed(2)
		}
	ACCESS read-write
	STATUS mandatory
	DESCRIPTION
		"The current state of this module's crossover
		configuration.  Setting this object to uncrossed(2)
		allows the last port to be used to connect to another
		repeater.  Often this feature is used to connect one 10BASE-T
		module to another."
	::= { ennMSRJ45SModEntry 3 }

ennMSRJ45SModDipCrossover OBJECT-TYPE
	SYNTAX INTEGER {
		crossed(1),
		uncrossed(2)
		}
	ACCESS read-only
	STATUS mandatory
	DESCRIPTION
		"The crossover configuration indicated by this module's
		dip switches."
	::= { ennMSRJ45SModEntry 4 }


ennMSRJ45SPortTable			 OBJECT-TYPE
	SYNTAX SEQUENCE OF EnnMSRJ45SPortEntry
	ACCESS not-accessible
	STATUS mandatory
	DESCRIPTION
		"A table of port-specific information for each port of
		this module type."
	::= { ennMSRJ45S 2 }

ennMSRJ45SPortEntry OBJECT-TYPE
	SYNTAX EnnMSRJ45SPortEntry
	ACCESS not-accessible
	STATUS mandatory
	DESCRIPTION
		"A port entry containing objects that describe this port."
	INDEX { ennMSRJ45SPortSlotIndex, ennMSRJ45SPortIndex }
	::= { ennMSRJ45SPortTable 1 }

EnnMSRJ45SPortEntry ::=
	SEQUENCE {
		ennMSRJ45SPortSlotIndex
			INTEGER,
		ennMSRJ45SPortIndex
			INTEGER,
		ennMSRJ45SPortAdminState
			INTEGER,
		ennMSRJ45SPortBuddySlot
			INTEGER,
		ennMSRJ45SPortBuddyPort
			INTEGER,
		ennMSRJ45SPortDipAdminState
			INTEGER,
		ennMSRJ45SPortLinkInteg
			INTEGER,
		ennMSRJ45SPortDipLinkInteg
			INTEGER,
		ennMSRJ45SPortSquelch
			INTEGER,
		ennMSRJ45SPortDipSquelch
			INTEGER
		}

	ennMSRJ45SPortSlotIndex OBJECT-TYPE
	SYNTAX INTEGER
	ACCESS read-only
	STATUS mandatory
	DESCRIPTION
		"The slot number of this port's module."
	::= { ennMSRJ45SPortEntry 1 }


ennMSRJ45SPortIndex OBJECT-TYPE
	SYNTAX INTEGER
	ACCESS read-only
	STATUS mandatory
	DESCRIPTION
		"The port number of this port."
	::= { ennMSRJ45SPortEntry 2 }

ennMSRJ45SPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennMSRJ45SPortEntry 3 }

ennMSRJ45SPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennMSRJ45SPortEntry 4 }

ennMSRJ45SPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennMSRJ45SPortEntry 5 }

ennMSRJ45SPortDipAdminState OBJECT-TYPE
	SYNTAX INTEGER {
		enabled(1),
		disabled(2)
		}
	ACCESS read-only
	STATUS mandatory
	DESCRIPTION
		"The state of this port as indicated by the port's dip
		switches."
	::= { ennMSRJ45SPortEntry 6 }

ennMSRJ45SPortLinkInteg OBJECT-TYPE
	SYNTAX INTEGER {
		enabled(1),
		disabled(2)
		}
	ACCESS read-write
	STATUS mandatory
	DESCRIPTION
		"The port's link integrity configuration.  Enabling
		link integrity configures the port to conform to
		the link integrity feature as specified by 10BASE-T."
	::= { ennMSRJ45SPortEntry 7 }

ennMSRJ45SPortDipLinkInteg OBJECT-TYPE
	SYNTAX INTEGER {
		enabled(1),
		disabled(2)
		}
	ACCESS read-only
	STATUS mandatory
	DESCRIPTION
		"The link integrity configuration as indicated by this
		port's dip switches."
	::= { ennMSRJ45SPortEntry 8 }

ennMSRJ45SPortSquelch	 OBJECT-TYPE
	SYNTAX INTEGER {
		normal(1),		-- high squelch
		low(2)
		}
	ACCESS read-write
	STATUS mandatory
	DESCRIPTION
		"The port's squelch configuration.  See the module's
		user's guide for more information."
	::= { ennMSRJ45SPortEntry 9 }

ennMSRJ45SPortDipSquelch	 OBJECT-TYPE
	SYNTAX INTEGER {
		normal(1),		-- high squelch
		low(2)
		}
	ACCESS read-only
	STATUS mandatory
	DESCRIPTION
		"The port's squelch configuration as indicated by this
		port's dip switches."
	::= { ennMSRJ45SPortEntry 10 }

--
-- Ethernet BNC Module
--


ennMSBNCModTable OBJECT-TYPE
	SYNTAX SEQUENCE OF EnnMSBNCModEntry
	ACCESS not-accessible
	STATUS mandatory
	DESCRIPTION
		"A list of module-specific information associated
		with a particular ennMS-BNC module in the concentrator."
	::= { ennMSBNC 1 }

ennMSBNCModEntry OBJECT-TYPE
	SYNTAX EnnMSBNCModEntry
	ACCESS not-accessible
	STATUS mandatory
	DESCRIPTION
		"A module entry containing objects that describe the
		module level for that particular module."
	INDEX { ennMSBNCModSlotIndex }
	::= { ennMSBNCModTable 1 }

EnnMSBNCModEntry ::=
	SEQUENCE {
		ennMSBNCModSlotIndex
			INTEGER,
		ennMSBNCModDipNetwork
			INTEGER
		}

ennMSBNCModSlotIndex OBJECT-TYPE
	SYNTAX INTEGER
	ACCESS read-only
	STATUS mandatory
	DESCRIPTION
		"The slot number of this module."
	::= { ennMSBNCModEntry 1 }

ennMSBNCModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSBNCModEntry 2 }

ennMSBNCPortTable OBJECT-TYPE
	SYNTAX SEQUENCE OF EnnMSBNCPortEntry
	ACCESS not-accessible
	STATUS mandatory
	DESCRIPTION
		"A table of port-specific information for each port of
		this module type."
	::= { ennMSBNC 2 }

ennMSBNCPortEntry OBJECT-TYPE
	SYNTAX EnnMSBNCPortEntry
	ACCESS not-accessible
	STATUS mandatory
	DESCRIPTION
		"A port entry containing objects that describe this port."
	INDEX { ennMSBNCPortSlotIndex, ennMSBNCPortIndex }
	::= { ennMSBNCPortTable 1 }

EnnMSBNCPortEntry ::=
	SEQUENCE {
		ennMSBNCPortSlotIndex
			INTEGER,
		ennMSBNCPortIndex
			INTEGER,
		ennMSBNCPortDipAdminState
			INTEGER,
		ennMSBNCPortDipTermination
			INTEGER,
		ennMSBNCPortDipGround
			INTEGER
		}

ennMSBNCPortSlotIndex OBJECT-TYPE
	SYNTAX INTEGER
	ACCESS read-only
	STATUS mandatory
	DESCRIPTION
		"The slot number of this port's module."
	::= { ennMSBNCPortEntry 1 }


ennMSBNCPortIndex OBJECT-TYPE
	SYNTAX INTEGER
	ACCESS read-only
	STATUS mandatory
	DESCRIPTION
		"The port number of this port."
	::= { ennMSBNCPortEntry 2 }

ennMSBNCPortDipAdminState OBJECT-TYPE
	SYNTAX INTEGER {
		enabled(1),
		disabled(2)
		}
	ACCESS read-only
	STATUS mandatory
	DESCRIPTION
		"The state of this port as indicated by the port's dip
		switches."
	::= { ennMSBNCPortEntry 3 }

ennMSBNCPortDipTermination OBJECT-TYPE
	SYNTAX INTEGER {
		terminated(1),
		not-terminated(2)
		}
	ACCESS read-only
	STATUS mandatory
	DESCRIPTION
		"The state of this port's termination as indicated by the
		port's dip switches."
	::= { ennMSBNCPortEntry 4 }

ennMSBNCPortDipGround OBJECT-TYPE
	SYNTAX INTEGER {
		grounded(1),
		not-grounded(2)
		}
	ACCESS read-only
	STATUS mandatory
	DESCRIPTION
		"The state of this port's ground as indicated by the port's
		dip switches."
	::= { ennMSBNCPortEntry 5 }

--
-- Ethernet to Ethernet Bridge Module
--

eennPSBRGModTable OBJECT-TYPE
	SYNTAX SEQUENCE OF EennPSBRGModEntry
	ACCESS not-accessible
	STATUS mandatory
	DESCRIPTION
		"A table of module-specific information for
		each eennPS-BRG module in the concentrator."
	::= { eennPSBRG 1 }

eennPSBRGModEntry OBJECT-TYPE
	SYNTAX EennPSBRGModEntry
	ACCESS not-accessible
	STATUS mandatory
	DESCRIPTION
		"A list of module-specific information about a specific
		eennPS-BRG module in the concentrator."
	INDEX { eennPSBRGModSlotIndex }
	::= { eennPSBRGModTable 1 }

EennPSBRGModEntry ::=
	SEQUENCE {
		eennPSBRGModSlotIndex
			INTEGER,
		eennPSBRGModStationAddr
			OCTET STRING,
		eennPSBRGModProtocols
			DisplayString
		}

eennPSBRGModSlotIndex OBJECT-TYPE
	SYNTAX INTEGER
	ACCESS read-only
	STATUS mandatory
	DESCRIPTION
		"The slot number of this module."
	::= { eennPSBRGModEntry 1 }

eennPSBRGModStationAddr OBJECT-TYPE
	SYNTAX OCTET STRING (SIZE(6))
	ACCESS read-only
	STATUS mandatory
	DESCRIPTION
		"A 6 octet address that uniquely identifies this module.
		The station address is the mac address of port 1."
	::= { eennPSBRGModEntry 2 }

eennPSBRGModProtocols OBJECT-TYPE
	SYNTAX DisplayString
	ACCESS read-only
	STATUS mandatory
	DESCRIPTION
		"A textual description of the protocols supported by
		this module"
	::= { eennPSBRGModEntry 3 }


eennPSBRGPortTable	OBJECT-TYPE
	SYNTAX SEQUENCE OF EennPSBRGPortEntry
	ACCESS not-accessible
	STATUS mandatory
	DESCRIPTION
		"A table of port-specific for each port of each
		eennPS-BRG module in the concentrator."
	::= { eennPSBRG 2 }


eennPSBRGPortEntry OBJECT-TYPE
	SYNTAX EennPSBRGPortEntry
	ACCESS not-accessible
	STATUS mandatory
	DESCRIPTION
		"A list of port-specific informatoin about a specific
		eennPS-BRG port in the concentrator."
	INDEX { eennPSBRGPortSlotIndex, eennPSBRGPortIndex }
	::= { eennPSBRGPortTable 1 }

EennPSBRGPortEntry ::=
	SEQUENCE {
		eennPSBRGPortSlotIndex
			INTEGER,
		eennPSBRGPortIndex
			INTEGER,
		eennPSBRGPortIpAddress
			IpAddress,
		eennPSBRGPortDipNetwork
			INTEGER,
		eennPSBRGPortDefNetwork
			INTEGER
		}

eennPSBRGPortSlotIndex OBJECT-TYPE
	SYNTAX INTEGER
	ACCESS read-only
	STATUS mandatory
	DESCRIPTION
		"The slot number for this port's module."
	::= { eennPSBRGPortEntry 1 }

eennPSBRGPortIndex OBJECT-TYPE
	SYNTAX INTEGER
	ACCESS read-only
	STATUS mandatory
	DESCRIPTION
		"The port number for this port within this slot."
	::= { eennPSBRGPortEntry 2 }

eennPSBRGPortIpAddress OBJECT-TYPE
	SYNTAX IpAddress
	ACCESS read-only
	STATUS mandatory
	DESCRIPTION
		"The IP Address associated with this port."
	::= { eennPSBRGPortEntry 3 }

eennPSBRGPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { eennPSBRGPortEntry 4 }

eennPSBRGPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the EBM's
		non-volatile storage."
	::= { eennPSBRGPortEntry 5 }

--
-- Ethernet to Serial Router Module
--


esnnPSRTRModTable OBJECT-TYPE
	SYNTAX SEQUENCE OF EsnnPSRTRModEntry
	ACCESS not-accessible
	STATUS mandatory
	DESCRIPTION
		"A table of module-specific information for
		each esnnPS-RTR module in the concentrator."
	::= { esnnPSRTR 1 }

esnnPSRTRModEntry OBJECT-TYPE
	SYNTAX EsnnPSRTRModEntry
	ACCESS not-accessible
	STATUS mandatory
	DESCRIPTION
		"A list of module-specific information about a specific
		esnnPS-RTR module in the concentrator."
	INDEX { esnnPSRTRModSlotIndex }
	::= { esnnPSRTRModTable 1 }

EsnnPSRTRModEntry ::=
	SEQUENCE {
		esnnPSRTRModSlotIndex
			INTEGER,
		esnnPSRTRModStationAddr
			OCTET STRING,
		esnnPSRTRModProtocols
			DisplayString
		}

esnnPSRTRModSlotIndex OBJECT-TYPE
	SYNTAX INTEGER
	ACCESS read-only
	STATUS mandatory
	DESCRIPTION
		"The slot number of this module."
	::= { esnnPSRTRModEntry 1 }

esnnPSRTRModStationAddr OBJECT-TYPE
	SYNTAX OCTET STRING (SIZE(6))
	ACCESS read-only
	STATUS mandatory
	DESCRIPTION
		"A 6 octet address that uniquely identifies this module.
		The station address is the mac address of port 1."
	::= { esnnPSRTRModEntry 2 }


esnnPSRTRModProtocols OBJECT-TYPE
	SYNTAX DisplayString
	ACCESS read-only
	STATUS mandatory
	DESCRIPTION
		"A textual description of the protocols supported by
		this module"
	::= { esnnPSRTRModEntry 3 }

esnnPSRTRPortTable	OBJECT-TYPE
	SYNTAX SEQUENCE OF EsnnPSRTRPortEntry
	ACCESS not-accessible
	STATUS mandatory
	DESCRIPTION
		"A table of port-specific for each port of each
		esnnPS-RTR module in the concentrator."
	::= { esnnPSRTR 2 }

esnnPSRTRPortEntry OBJECT-TYPE
	SYNTAX EsnnPSRTRPortEntry
	ACCESS not-accessible
	STATUS mandatory
	DESCRIPTION
		"A list of port-specific informatoin about a specific
		esnnPS-RTR port in the concentrator."
	INDEX { esnnPSRTRPortSlotIndex, esnnPSRTRPortIndex }
	::= { esnnPSRTRPortTable 1 }

EsnnPSRTRPortEntry ::=
	SEQUENCE {
		esnnPSRTRPortSlotIndex
			INTEGER,
		esnnPSRTRPortIndex
			INTEGER,
		esnnPSRTRPortIpAddress
			IpAddress,
		esnnPSRTRPortDipNetwork
			INTEGER,
		esnnPSRTRPortDefNetwork
			INTEGER
		}

esnnPSRTRPortSlotIndex OBJECT-TYPE
	SYNTAX INTEGER
	ACCESS read-only
	STATUS mandatory
	DESCRIPTION
		"The slot number for this port's module."
	::= { esnnPSRTRPortEntry 1 }

esnnPSRTRPortIndex OBJECT-TYPE
	SYNTAX INTEGER
	ACCESS read-only
	STATUS mandatory
	DESCRIPTION
		"The port number for this port."
	::= { esnnPSRTRPortEntry 2 }

esnnPSRTRPortIpAddress OBJECT-TYPE
	SYNTAX IpAddress
	ACCESS read-only
	STATUS mandatory
	DESCRIPTION
		"The IP Address associated with this port."
	::= { esnnPSRTRPortEntry 3 }

esnnPSRTRPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { esnnPSRTRPortEntry 4 }

esnnPSRTRPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OERM's
		non-volatile storage."
	::= { esnnPSRTRPortEntry 5 }

--
-- Ethernet to Ethernet Router Module
--


eennPSRTRModTable OBJECT-TYPE
	SYNTAX SEQUENCE OF EennPSRTRModEntry
	ACCESS not-accessible
	STATUS mandatory
	DESCRIPTION
		"A table of module-specific information for
		each eennPS-RTR module in the concentrator."
	::= { eennPSRTR 1 }

eennPSRTRModEntry OBJECT-TYPE
	SYNTAX EennPSRTRModEntry
	ACCESS not-accessible
	STATUS mandatory
	DESCRIPTION
		"A list of module-specific information about a specific
		eennPS-RTR module in the concentrator."
	INDEX { eennPSRTRModSlotIndex }
	::= { eennPSRTRModTable 1 }

EennPSRTRModEntry ::=
	SEQUENCE {
		eennPSRTRModSlotIndex
			INTEGER,
		eennPSRTRModStationAddr
			OCTET STRING,
		eennPSRTRModProtocols
			DisplayString
		}

eennPSRTRModSlotIndex OBJECT-TYPE
	SYNTAX INTEGER
	ACCESS read-only
	STATUS mandatory
	DESCRIPTION
		"The slot number of this module."
	::= { eennPSRTRModEntry 1 }

eennPSRTRModStationAddr OBJECT-TYPE
	SYNTAX OCTET STRING (SIZE(6))
	ACCESS read-only
	STATUS mandatory
	DESCRIPTION
		"A 6 octet address that uniquely identifies this module.
		The station address is the mac address of port 1."
	::= { eennPSRTRModEntry 2 }


eennPSRTRModProtocols OBJECT-TYPE
	SYNTAX DisplayString
	ACCESS read-only
	STATUS mandatory
	DESCRIPTION
		"A textual description of the protocols supported by
		this module"
	::= { eennPSRTRModEntry 3 }

eennPSRTRPortTable	OBJECT-TYPE
	SYNTAX SEQUENCE OF EennPSRTRPortEntry
	ACCESS not-accessible
	STATUS mandatory
	DESCRIPTION
		"A table of port-specific for each port of each
		eennPS-RTR module in the concentrator."
	::= { eennPSRTR 2 }

eennPSRTRPortEntry OBJECT-TYPE
	SYNTAX EennPSRTRPortEntry
	ACCESS not-accessible
	STATUS mandatory
	DESCRIPTION
		"A list of port-specific informatoin about a specific
		eennPS-RTR port in the concentrator."
	INDEX { eennPSRTRPortSlotIndex, eennPSRTRPortIndex }
	::= { eennPSRTRPortTable 1 }

EennPSRTRPortEntry ::=
	SEQUENCE {
		eennPSRTRPortSlotIndex
			INTEGER,
		eennPSRTRPortIndex
			INTEGER,
		eennPSRTRPortIpAddress
			IpAddress,
		eennPSRTRPortDipNetwork
			INTEGER,
		eennPSRTRPortDefNetwork
			INTEGER
		}

eennPSRTRPortSlotIndex OBJECT-TYPE
	SYNTAX INTEGER
	ACCESS read-only
	STATUS mandatory
	DESCRIPTION
		"The slot number for this port's module."
	::= { eennPSRTRPortEntry 1 }

eennPSRTRPortIndex OBJECT-TYPE
	SYNTAX INTEGER
	ACCESS read-only
	STATUS mandatory
	DESCRIPTION
		"The port number of this port."
	::= { eennPSRTRPortEntry 2 }

eennPSRTRPortIpAddress OBJECT-TYPE
	SYNTAX IpAddress
	ACCESS read-only
	STATUS mandatory
	DESCRIPTION
		"The IP Address associated with this port."
	::= { eennPSRTRPortEntry 3 }

eennPSRTRPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { eennPSRTRPortEntry 4 }

eennPSRTRPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OERM's
		non-volatile storage."
	::= { eennPSRTRPortEntry 5 }

--
-- Ethernet Female AUI Module
--

ennPSAUIFModTable OBJECT-TYPE
	SYNTAX SEQUENCE OF EnnPSAUIFModEntry
	ACCESS not-accessible
	STATUS mandatory
	DESCRIPTION
		"A list of module-specific information associated
		with a particular ennPS-AUIF module in the concentrator."
	::= { ennPSAUIF 1 }

ennPSAUIFModEntry OBJECT-TYPE
	SYNTAX EnnPSAUIFModEntry
	ACCESS not-accessible
	STATUS mandatory
	DESCRIPTION
		"A list of module-specific information about a specific
		ennPS-AUIF module in the concentrator."
	INDEX { ennPSAUIFModSlotIndex }
	::= { ennPSAUIFModTable 1 }

EnnPSAUIFModEntry ::=
	SEQUENCE {
		ennPSAUIFModSlotIndex
			INTEGER
		}

ennPSAUIFModSlotIndex OBJECT-TYPE
	SYNTAX INTEGER
	ACCESS read-only
	STATUS mandatory
	DESCRIPTION
		"The slot number of this module."
	::= { ennPSAUIFModEntry 1 }

ennPSAUIFPortTable OBJECT-TYPE
	SYNTAX SEQUENCE OF EnnPSAUIFPortEntry
	ACCESS not-accessible
	STATUS mandatory
	DESCRIPTION
		"A table of port-specific information for each port of
		this module type."
	::= { ennPSAUIF 2 }

ennPSAUIFPortEntry OBJECT-TYPE
	SYNTAX EnnPSAUIFPortEntry
	ACCESS not-accessible
	STATUS mandatory
	DESCRIPTION
		"A list of module-specific information about a specific
		ennPS-AUIF port in the concentrator."
	INDEX { ennPSAUIFPortSlotIndex, ennPSAUIFPortIndex }
	::= { ennPSAUIFPortTable 1 }

EnnPSAUIFPortEntry ::=
	SEQUENCE {
		ennPSAUIFPortSlotIndex
			INTEGER,
		ennPSAUIFPortIndex
			INTEGER,
		ennPSAUIFPortAdminState
			INTEGER,
		ennPSAUIFPortBuddySlot
			INTEGER,
		ennPSAUIFPortBuddyPort
			INTEGER,
		ennPSAUIFPortDipAdminState
			INTEGER,
		ennPSAUIFPortDipNetwork
			INTEGER
		}

ennPSAUIFPortSlotIndex OBJECT-TYPE
	SYNTAX INTEGER
	ACCESS read-only
	STATUS mandatory
	DESCRIPTION
		"The slot number of this port's module."
	::= { ennPSAUIFPortEntry 1 }


ennPSAUIFPortIndex OBJECT-TYPE
	SYNTAX INTEGER
	ACCESS read-only
	STATUS mandatory
	DESCRIPTION
		"The port number of this port."
	::= { ennPSAUIFPortEntry 2 }

ennPSAUIFPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennPSAUIFPortEntry 3 }

ennPSAUIFPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennPSAUIFPortEntry 4 }

ennPSAUIFPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennPSAUIFPortEntry 5 }

ennPSAUIFPortDipAdminState OBJECT-TYPE
	SYNTAX INTEGER {
		enabled(1),
		disabled(2),
		redundant-primary(3),
		redundant-backup(4)
		}
	ACCESS read-only
	STATUS mandatory
	DESCRIPTION
		"The state of this port as indicated by the port's dip
		switches."
	::= { ennPSAUIFPortEntry 6 }


ennPSAUIFPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ennPSAUIFPortEntry 7 }


--
-- Ethernet Male AUI Module
--

ennPSAUIMModTable OBJECT-TYPE
	SYNTAX SEQUENCE OF EnnPSAUIMModEntry
	ACCESS not-accessible
	STATUS mandatory
	DESCRIPTION
		"A list of module-specific information associated
		with a particular ennPS-AUIM module in the concentrator."
	::= { ennPSAUIM 1 }

ennPSAUIMModEntry OBJECT-TYPE
	SYNTAX EnnPSAUIMModEntry
	ACCESS not-accessible
	STATUS mandatory
	DESCRIPTION
		"A list of module-specific information about a specific
		ennPS-AUIM module in the concentrator."
	INDEX { ennPSAUIMModSlotIndex }
	::= { ennPSAUIMModTable 1 }

EnnPSAUIMModEntry ::=
	SEQUENCE {
		ennPSAUIMModSlotIndex
			INTEGER
		}

ennPSAUIMModSlotIndex OBJECT-TYPE
	SYNTAX INTEGER
	ACCESS read-only
	STATUS mandatory
	DESCRIPTION
		"The slot number of this module."
	::= { ennPSAUIMModEntry 1 }

ennPSAUIMPortTable			 OBJECT-TYPE
	SYNTAX SEQUENCE OF EnnPSAUIMPortEntry
	ACCESS not-accessible
	STATUS mandatory
	DESCRIPTION
		"A table of port-specific information for each port of
		this module type."
	::= { ennPSAUIM 2 }

ennPSAUIMPortEntry OBJECT-TYPE
	SYNTAX EnnPSAUIMPortEntry
	ACCESS not-accessible
	STATUS mandatory
	DESCRIPTION
		"A list of module-specific information about a specific
		ennPS-AUIM port in the concentrator."
	INDEX { ennPSAUIMPortSlotIndex, ennPSAUIMPortIndex }
	::= { ennPSAUIMPortTable 1 }

EnnPSAUIMPortEntry ::=
	SEQUENCE {
		ennPSAUIMPortSlotIndex
			INTEGER,
		ennPSAUIMPortIndex
			INTEGER,
		ennPSAUIMPortAdminState
			INTEGER,
		ennPSAUIMPortBuddySlot
			INTEGER,
		ennPSAUIMPortBuddyPort
			INTEGER,
		ennPSAUIMPortDipAdminState
			INTEGER,
		ennPSAUIMPortDipNetwork
			INTEGER,
		ennPSAUIMPortSQETest
			INTEGER,
		ennPSAUIMPortDipSQETest
			INTEGER,
		ennPSAUIMPortCollision
			INTEGER,
		ennPSAUIMPortDipCollision
			INTEGER,
		ennPSAUIMPortHalfStep
			INTEGER,
		ennPSAUIMPortDipHalfStep
			INTEGER
		}

ennPSAUIMPortSlotIndex OBJECT-TYPE
	SYNTAX INTEGER
	ACCESS read-only
	STATUS mandatory
	DESCRIPTION
		"The slot number of this port's module."
	::= { ennPSAUIMPortEntry 1 }


ennPSAUIMPortIndex OBJECT-TYPE
	SYNTAX INTEGER
	ACCESS read-only
	STATUS mandatory
	DESCRIPTION
		"The port number of this port."
	::= { ennPSAUIMPortEntry 2 }

ennPSAUIMPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennPSAUIMPortEntry 3 }

ennPSAUIMPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennPSAUIMPortEntry 4 }

ennPSAUIMPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennPSAUIMPortEntry 5 }

ennPSAUIMPortDipAdminState OBJECT-TYPE
	SYNTAX INTEGER {
		enabled(1),
		disabled(2)
		}
	ACCESS read-only
	STATUS mandatory
	DESCRIPTION
		"The state of this port as indicated by the port's dip
		switches."
	::= { ennPSAUIMPortEntry 6 }

ennPSAUIMPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ennPSAUIMPortEntry 7 }

ennPSAUIMPortSQETest OBJECT-TYPE
	SYNTAX INTEGER {
		enabled(1),
		disabled(2)
		}
	ACCESS read-write
	STATUS mandatory
	DESCRIPTION
		"The current SQE test configuration for this port."
	::= { ennPSAUIMPortEntry 8 }

ennPSAUIMPortDipSQETest OBJECT-TYPE
	SYNTAX INTEGER {
		enabled(1),
		disabled(2)
		}
	ACCESS read-only
	STATUS mandatory
	DESCRIPTION
		"The SQE test configuration for this port as indicated
		by the port's dip switches."
	::= { ennPSAUIMPortEntry 9 }

ennPSAUIMPortCollision OBJECT-TYPE
	SYNTAX INTEGER {
		normal(1),
		alternate(2)
		}
	ACCESS read-write
	STATUS mandatory
	DESCRIPTION
		"The current collision configuration for this port."
	::= { ennPSAUIMPortEntry 10 }

ennPSAUIMPortDipCollision OBJECT-TYPE
	SYNTAX INTEGER {
		normal(1),
		alternate(2)
		}
	ACCESS read-only
	STATUS mandatory
	DESCRIPTION
		"The collision configuration for this port as indicated
		by the port's dip switches."
	::= { ennPSAUIMPortEntry 11 }

ennPSAUIMPortHalfStep OBJECT-TYPE
	SYNTAX INTEGER {
		enabled(1),
		disabled(2)
		}
	ACCESS read-write
	STATUS mandatory
	DESCRIPTION
		"The current step configuration for this port."
	::= { ennPSAUIMPortEntry 12 }

ennPSAUIMPortDipHalfStep OBJECT-TYPE
	SYNTAX INTEGER {
		enabled(1),
		disabled(2)
		}
	ACCESS read-only
	STATUS mandatory
	DESCRIPTION
		"The step configuration for this port as indicated
		by the port's dip switches."
	::= { ennPSAUIMPortEntry 13 }

--
-- Token Ring 8-Port MAU Module
--
t08MSRJ45SModTable OBJECT-TYPE
	SYNTAX SEQUENCE OF T08MSRJ45SModEntry
	ACCESS not-accessible
	STATUS mandatory
	DESCRIPTION
		"A list of module-specific information associated
		with a particular t08MS-RJ45S module in the concentrator."
	::= { t08MSRJ45S 1 }

t08MSRJ45SModEntry OBJECT-TYPE
	SYNTAX T08MSRJ45SModEntry
	ACCESS not-accessible
	STATUS mandatory
	DESCRIPTION
		"A description of the t08MS-RJ45S module attributes."
	INDEX { t08MSRJ45SModSlotIndex }
	::= { t08MSRJ45SModTable 1 }

T08MSRJ45SModEntry ::=
	SEQUENCE {
		t08MSRJ45SModSlotIndex
			INTEGER,
		t08MSRJ45SModBypsAdminState
			INTEGER,
		t08MSRJ45SModBypsOperState
			INTEGER,
		t08MSRJ45SModDipCableImp
			INTEGER
		}

t08MSRJ45SModSlotIndex OBJECT-TYPE
	SYNTAX INTEGER
	ACCESS read-only
	STATUS mandatory
	DESCRIPTION
		"The slot number of this module."
	::= { t08MSRJ45SModEntry 1 }


t08MSRJ45SModBypsAdminState OBJECT-TYPE
	SYNTAX INTEGER {
		insert(1),
		bypass(2)
		}
	ACCESS read-write
	STATUS mandatory
	DESCRIPTION
		"The desired state of this module with respect
		to the ring.  Setting this attribute to bypass(2)
		will cause this module to be removed from the ring
		that passes through the module's ring in and ring out
		ports."
	::= { t08MSRJ45SModEntry 2 }

t08MSRJ45SModBypsOperState OBJECT-TYPE
	SYNTAX INTEGER {
		insert(1),
		bypass(2)
		}
	ACCESS read-only
	STATUS mandatory
	DESCRIPTION
		"The operational state of this module with respect
		to the ring.  If this attribute is equal to bypass(2),
		then the module has been removed from the ring that
		passes through the module's ring in and ring out ports."
	::= { t08MSRJ45SModEntry 3 }

t08MSRJ45SModDipCableImp OBJECT-TYPE
	SYNTAX INTEGER {
		ohm100(1),
		ohm150(2)
		}
	ACCESS read-only
	STATUS mandatory
	DESCRIPTION
		"The setting of this module's port impedance matching, with
		100 ohm corresponding to unshielded twisted pair cabling and
		150 ohm corresponding to shielded twisted pair cabling.
		This setting is valid for all ports on this module."
	::= { t08MSRJ45SModEntry 4 }


t08MSRJ45SPortTable OBJECT-TYPE
	SYNTAX SEQUENCE OF T08MSRJ45SPortEntry
	ACCESS not-accessible
	STATUS mandatory
	DESCRIPTION
		"A table of port-specific information for each port of
		this module type."
	::= { t08MSRJ45S 2 }

t08MSRJ45SPortEntry OBJECT-TYPE
	SYNTAX T08MSRJ45SPortEntry
	ACCESS not-accessible
	STATUS mandatory
	DESCRIPTION
		"A description of t08MS-RJ45S port attributes."
	INDEX { t08MSRJ45SPortSlotIndex, t08MSRJ45SPortIndex }
	::= { t08MSRJ45SPortTable 1 }

T08MSRJ45SPortEntry ::=
	SEQUENCE {
		t08MSRJ45SPortSlotIndex
			INTEGER,
		t08MSRJ45SPortIndex
			INTEGER,
		t08MSRJ45SPortDipAdminState
			INTEGER,
		t08MSRJ45SPortStationType
			INTEGER
		}

t08MSRJ45SPortSlotIndex OBJECT-TYPE
	SYNTAX INTEGER
	ACCESS read-only
	STATUS mandatory
	DESCRIPTION
		"The slot number of this port's module."
	::= { t08MSRJ45SPortEntry 1 }


t08MSRJ45SPortIndex OBJECT-TYPE
	SYNTAX INTEGER
	ACCESS read-only
	STATUS mandatory
	DESCRIPTION
		"The port number of this port."
	::= { t08MSRJ45SPortEntry 2 }

t08MSRJ45SPortDipAdminState OBJECT-TYPE
	SYNTAX INTEGER {
		enabled(1),
		disabled(2)
		}
	ACCESS read-only
	STATUS mandatory
	DESCRIPTION
		"The state of this port as indicated by the port's dip
		switches."
	::= { t08MSRJ45SPortEntry 3 }

t08MSRJ45SPortStationType OBJECT-TYPE
	SYNTAX INTEGER {
		mac-present(1),
		mac-not-present(2)
		}
	ACCESS read-write
	STATUS mandatory
	DESCRIPTION
		"Determines whether the station connected to this port
		has a MAC address."
	::= { t08MSRJ45SPortEntry 4 }

t08MSRJ45STrunkTable OBJECT-TYPE
	SYNTAX SEQUENCE OF T08MSRJ45STrunkEntry
	ACCESS not-accessible
	STATUS mandatory
	DESCRIPTION
		"A list of trunk-specific information about each trunk
		for this module type."
	::= { t08MSRJ45S 3 }

t08MSRJ45STrunkEntry OBJECT-TYPE
	SYNTAX T08MSRJ45STrunkEntry
	ACCESS not-accessible
	STATUS mandatory
	DESCRIPTION
		"A description of t08MS-RJ45S trunk attributes."
	INDEX { t08MSRJ45STrunkSlotIndex, t08MSRJ45STrunkIndex }
	::= { t08MSRJ45STrunkTable 1 }

T08MSRJ45STrunkEntry ::=
	SEQUENCE {
		t08MSRJ45STrunkSlotIndex
			INTEGER,
		t08MSRJ45STrunkIndex
			INTEGER,
		t08MSRJ45STrunkDipAdminState
			INTEGER,
		t08MSRJ45STrunkCableMon
			INTEGER,
		t08MSRJ45STrunkDipCableMon
			INTEGER,
		t08MSRJ45STrunkNetMapState
			INTEGER,
		t08MSRJ45STrunkExtBcnRecovery
			INTEGER
		}

t08MSRJ45STrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { t08MSRJ45STrunkEntry 1 }


t08MSRJ45STrunkIndex OBJECT-TYPE
	SYNTAX INTEGER
	ACCESS read-only
	STATUS mandatory
	DESCRIPTION
		"The trunk number for this trunk."
	::= { t08MSRJ45STrunkEntry 2 }

t08MSRJ45STrunkDipAdminState OBJECT-TYPE
	SYNTAX INTEGER {
		enabled(1),
		disabled(2)
		}
	ACCESS read-only
	STATUS mandatory
	DESCRIPTION
		"The state of this trunk as indicated by the trunk's dip
		switches."
	::= { t08MSRJ45STrunkEntry 3 }


t08MSRJ45STrunkCableMon OBJECT-TYPE
	SYNTAX INTEGER {
		enabled(1),
		disabled(2),
		notApplicable(3)
	}
	ACCESS read-write
	STATUS mandatory
	DESCRIPTION
		"The cable monitor configuration for this trunk."
	::= { t08MSRJ45STrunkEntry 4 }

t08MSRJ45STrunkDipCableMon OBJECT-TYPE
	SYNTAX INTEGER {
		enabled(1),
		disabled(2),
		notApplicable(3)
	}
	ACCESS read-only
	STATUS mandatory
	DESCRIPTION
		"The cable monitor configuration as indicated by this trunk's
		dip switches."
	::= { t08MSRJ45STrunkEntry 5 }


t08MSRJ45STrunkNetMapState OBJECT-TYPE
	SYNTAX INTEGER {
		notApplicable(1),
		internal(2),
		external(3)
	}
	ACCESS read-write
	STATUS mandatory
	DESCRIPTION
		"The map state of the copper ring-in trunk.  This
		should be set to external for ring-in trunks which
		connect to external hubs.  The mapping logic will not
		operate on trunks which are set to external.  This
		prevents incorrect mapping which can occur when a
		module in one hub detects the mapping signal from
		another hub. This attribute only applies to copper
		ring-in trunks."
	::= { t08MSRJ45STrunkEntry 6 }


t08MSRJ45STrunkExtBcnRecovery OBJECT-TYPE
	SYNTAX INTEGER {
		exists(1),
		nonExists(2),
		notApplicable(3)
	}
	ACCESS read-write
	STATUS mandatory
	DESCRIPTION
		"Indicates whether the trunk is connected to a
		segment that will perform beacon recovery.  This
		should be set to exists(1) for trunks which connect
		to hubs which perform beacon recovery.  This attribute
		is used to determine the fault domain when resolving a
		beaconing condition.

		The beacon recovery process will resolve beaconing on
		trunks with this attribute set to nonExists(2) before
		trunks with the attribute set to exists(1) are resolved.
		For backplane trunks, setting to a value other than
		notApplicable will return invalidData error.  The
		default value is nonExists(2)."
	::= { t08MSRJ45STrunkEntry 7 }


--
-- Ethernet Fiber Per-Port Module
--

ennPSFIBModTable OBJECT-TYPE
	SYNTAX SEQUENCE OF EnnPSFIBModEntry
	ACCESS not-accessible
	STATUS mandatory
	DESCRIPTION
		"A list of module-specific information associated
		with a particular ennPS-FIB module in the concentrator."
	::= { ennPSFIB 1 }

ennPSFIBModEntry OBJECT-TYPE
	SYNTAX EnnPSFIBModEntry
	ACCESS not-accessible
	STATUS mandatory
	DESCRIPTION
		"A list of module-specific information about a specific
		ennPS-FIB module in the concentrator."
	INDEX { ennPSFIBModSlotIndex }
	::= { ennPSFIBModTable 1 }

EnnPSFIBModEntry ::=
	SEQUENCE {
		ennPSFIBModSlotIndex
			INTEGER
		}

ennPSFIBModSlotIndex OBJECT-TYPE
	SYNTAX INTEGER
	ACCESS read-only
	STATUS mandatory
	DESCRIPTION
		"The slot number of this module."
	::= { ennPSFIBModEntry 1 }

ennPSFIBPortTable			 OBJECT-TYPE
	SYNTAX SEQUENCE OF EnnPSFIBPortEntry
	ACCESS not-accessible
	STATUS mandatory
	DESCRIPTION
		"A table of port-specific information for each port of
		this module type."
	::= { ennPSFIB 2 }

ennPSFIBPortEntry OBJECT-TYPE
	SYNTAX EnnPSFIBPortEntry
	ACCESS not-accessible
	STATUS mandatory
	DESCRIPTION
		"A list of module-specific information about a specific
		ennPS-FIB port in the concentrator."
	INDEX { ennPSFIBPortSlotIndex, ennPSFIBPortIndex }
	::= { ennPSFIBPortTable 1 }

EnnPSFIBPortEntry ::=
	SEQUENCE {
		ennPSFIBPortSlotIndex
			INTEGER,
		ennPSFIBPortIndex
			INTEGER,
		ennPSFIBPortAdminState
			INTEGER,
		ennPSFIBPortBuddySlot
			INTEGER,
		ennPSFIBPortBuddyPort
			INTEGER,
		ennPSFIBPortDipAdminState
			INTEGER,
		ennPSFIBPortDipNetwork
			INTEGER,
		ennPSFIBPortLLW
			INTEGER,
		ennPSFIBPortDipLLW
			INTEGER,
		ennPSFIBPortHipwr
			INTEGER,
		ennPSFIBPortDipHipwr
			INTEGER
		}

ennPSFIBPortSlotIndex OBJECT-TYPE
	SYNTAX INTEGER
	ACCESS read-only
	STATUS mandatory
	DESCRIPTION
		"The slot number of this port's module."
	::= { ennPSFIBPortEntry 1 }


ennPSFIBPortIndex OBJECT-TYPE
	SYNTAX INTEGER
	ACCESS read-only
	STATUS mandatory
	DESCRIPTION
		"The port number of this port."
	::= { ennPSFIBPortEntry 2 }

ennPSFIBPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennPSFIBPortEntry 3 }

ennPSFIBPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennPSFIBPortEntry 4 }

ennPSFIBPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennPSFIBPortEntry 5 }

ennPSFIBPortDipAdminState OBJECT-TYPE
	SYNTAX INTEGER {
		enabled(1),
		disabled(2),
		redundant-primary(3),
		redundant-backup(4)
		}
	ACCESS read-only
	STATUS mandatory
	DESCRIPTION
		"The state of this port as indicated by the port's dip
		switches."
	::= { ennPSFIBPortEntry 6 }

ennPSFIBPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ennPSFIBPortEntry 7 }

ennPSFIBPortLLW OBJECT-TYPE
	SYNTAX INTEGER {
		enabled(1),
		disabled(2)
		}
	ACCESS read-write
	STATUS mandatory
	DESCRIPTION
		"The current low light warning configuration for this port."
	::= { ennPSFIBPortEntry 8 }

ennPSFIBPortDipLLW OBJECT-TYPE
	SYNTAX INTEGER {
		enabled(1),
		disabled(2)
		}
	ACCESS read-only
	STATUS mandatory
	DESCRIPTION
		"The low light warning configuration indicated by this module's
		dip switches."
	::= { ennPSFIBPortEntry 9 }

ennPSFIBPortHipwr OBJECT-TYPE
	SYNTAX INTEGER {
		enabled(1),
		disabled(2)
		}
	ACCESS read-write
	STATUS mandatory
	DESCRIPTION
		"The current high power optic configuration for this port."
	::= { ennPSFIBPortEntry 10 }

ennPSFIBPortDipHipwr OBJECT-TYPE
	SYNTAX INTEGER {
		enabled(1),
		disabled(2)
		}
	ACCESS read-only
	STATUS mandatory
	DESCRIPTION
		"The high power optic configuration for this port as indicated
		by the port's dip switches."
	::= { ennPSFIBPortEntry 11 }

--
-- Ethernet 10BASE-F Per-Port Module
--

ennPSFBPModTable OBJECT-TYPE
	SYNTAX SEQUENCE OF EnnPSFBPModEntry
	ACCESS not-accessible
	STATUS mandatory
	DESCRIPTION
		"A list of module-specific information associated
		with a particular ennPS-FBP module in the concentrator."
	::= { ennPSFBP 1 }

ennPSFBPModEntry OBJECT-TYPE
	SYNTAX EnnPSFBPModEntry
	ACCESS not-accessible
	STATUS mandatory
	DESCRIPTION
		"A list of module-specific information about a specific
		ennPS-FBP module in the concentrator."
	INDEX { ennPSFBPModSlotIndex }
	::= { ennPSFBPModTable 1 }

EnnPSFBPModEntry ::=
	SEQUENCE {
		ennPSFBPModSlotIndex
			INTEGER
		}

ennPSFBPModSlotIndex OBJECT-TYPE
	SYNTAX INTEGER
	ACCESS read-only
	STATUS mandatory
	DESCRIPTION
		"The slot number of this module."
	::= { ennPSFBPModEntry 1 }

ennPSFBPPortTable			 OBJECT-TYPE
	SYNTAX SEQUENCE OF EnnPSFBPPortEntry
	ACCESS not-accessible
	STATUS mandatory
	DESCRIPTION
		"A table of port-specific information for each port of
		this module type."
	::= { ennPSFBP 2 }

ennPSFBPPortEntry OBJECT-TYPE
	SYNTAX EnnPSFBPPortEntry
	ACCESS not-accessible
	STATUS mandatory
	DESCRIPTION
		"A list of module-specific information about a specific
		ennPS-FBP port in the concentrator."
	INDEX { ennPSFBPPortSlotIndex, ennPSFBPPortIndex }
	::= { ennPSFBPPortTable 1 }

EnnPSFBPPortEntry ::=
	SEQUENCE {
		ennPSFBPPortSlotIndex
			INTEGER,
		ennPSFBPPortIndex
			INTEGER,
		ennPSFBPPortAdminState
			INTEGER,
		ennPSFBPPortBuddySlot
			INTEGER,
		ennPSFBPPortBuddyPort
			INTEGER,
		ennPSFBPPortDipAdminState
			INTEGER,
		ennPSFBPPortDipNetwork
			INTEGER,
		ennPSFBPPortLLW
			INTEGER,
		ennPSFBPPortDipLLW
			INTEGER,
		ennPSFBPPortHipwr
			INTEGER,
		ennPSFBPPortDipHipwr
			INTEGER
		}

ennPSFBPPortSlotIndex OBJECT-TYPE
	SYNTAX INTEGER
	ACCESS read-only
	STATUS mandatory
	DESCRIPTION
		"The slot number of this port's module."
	::= { ennPSFBPPortEntry 1 }


ennPSFBPPortIndex OBJECT-TYPE
	SYNTAX INTEGER
	ACCESS read-only
	STATUS mandatory
	DESCRIPTION
		"The port number of this port."
	::= { ennPSFBPPortEntry 2 }

ennPSFBPPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennPSFBPPortEntry 3 }

ennPSFBPPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennPSFBPPortEntry 4 }

ennPSFBPPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennPSFBPPortEntry 5 }

ennPSFBPPortDipAdminState OBJECT-TYPE
	SYNTAX INTEGER {
		enabled(1),
		disabled(2),
		redundant-primary(3),
		redundant-backup(4)
		}
	ACCESS read-only
	STATUS mandatory
	DESCRIPTION
		"The state of this port as indicated by the port's dip
		switches."
	::= { ennPSFBPPortEntry 6 }

ennPSFBPPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ennPSFBPPortEntry 7 }

ennPSFBPPortLLW OBJECT-TYPE
	SYNTAX INTEGER {
		enabled(1),
		disabled(2)
		}
	ACCESS read-write
	STATUS mandatory
	DESCRIPTION
		"The current low light warning configuration for this port."
	::= { ennPSFBPPortEntry 8 }

ennPSFBPPortDipLLW OBJECT-TYPE
	SYNTAX INTEGER {
		enabled(1),
		disabled(2)
		}
	ACCESS read-only
	STATUS mandatory
	DESCRIPTION
		"The low light warning configuration indicated by this module's
		dip switches."
	::= { ennPSFBPPortEntry 9 }

ennPSFBPPortHipwr OBJECT-TYPE
	SYNTAX INTEGER {
		enabled(1),
		disabled(2)
		}
	ACCESS read-write
	STATUS mandatory
	DESCRIPTION
		"The current high power optic configuration for this port."
	::= { ennPSFBPPortEntry 10 }

ennPSFBPPortDipHipwr OBJECT-TYPE
	SYNTAX INTEGER {
		enabled(1),
		disabled(2)
		}
	ACCESS read-only
	STATUS mandatory
	DESCRIPTION
		"The high power optic configuration for this port as indicated
		by the port's dip switches."
	::= { ennPSFBPPortEntry 11 }

--
-- Ethernet 10BASE-T Module
--

ennMSTELCOModTable OBJECT-TYPE
	SYNTAX SEQUENCE OF EnnMSTELCOModEntry
	ACCESS not-accessible
	STATUS mandatory
	DESCRIPTION
		"A list of module-specific information associated
		with a particular ennMS-TELCO module in the concentrator."
	::= { ennMSTELCO 1 }

ennMSTELCOModEntry OBJECT-TYPE
	SYNTAX EnnMSTELCOModEntry
	ACCESS not-accessible
	STATUS mandatory
	DESCRIPTION
		"A list of module-specific information about a specific
		ennMS-TELCO module in the concentrator."
	INDEX { ennMSTELCOModSlotIndex }
	::= { ennMSTELCOModTable 1 }

EnnMSTELCOModEntry ::=
	SEQUENCE {
		ennMSTELCOModSlotIndex
			INTEGER,
		ennMSTELCOModDipNetwork
			INTEGER
		}

ennMSTELCOModSlotIndex OBJECT-TYPE
	SYNTAX INTEGER
	ACCESS read-only
	STATUS mandatory
	DESCRIPTION
		"The slot number of this module."
	::= { ennMSTELCOModEntry 1 }

ennMSTELCOModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSTELCOModEntry 2 }

ennMSTELCOPortTable			 OBJECT-TYPE
	SYNTAX SEQUENCE OF EnnMSTELCOPortEntry
	ACCESS not-accessible
	STATUS mandatory
	DESCRIPTION
		"A table of port-specific information for each port of
		this module type."
	::= { ennMSTELCO 2 }

ennMSTELCOPortEntry OBJECT-TYPE
	SYNTAX EnnMSTELCOPortEntry
	ACCESS not-accessible
	STATUS mandatory
	DESCRIPTION
		"A list of module-specific information about a specific
		ennMS-TELCO port in the concentrator."
	INDEX { ennMSTELCOPortSlotIndex, ennMSTELCOPortIndex }
	::= { ennMSTELCOPortTable 1 }

EnnMSTELCOPortEntry ::=
	SEQUENCE {
		ennMSTELCOPortSlotIndex
			INTEGER,
		ennMSTELCOPortIndex
			INTEGER,
		ennMSTELCOPortAdminState
			INTEGER,
		ennMSTELCOPortBuddySlot
			INTEGER,
		ennMSTELCOPortBuddyPort
			INTEGER,
		ennMSTELCOPortDipAdminState
			INTEGER,
		ennMSTELCOPortLinkInteg
			INTEGER,
		ennMSTELCOPortDipLinkInteg
			INTEGER,
		ennMSTELCOPortSquelch
			INTEGER,
		ennMSTELCOPortJabber
			INTEGER,
		ennMSTELCOPortDipJabber
			INTEGER
		}

ennMSTELCOPortSlotIndex OBJECT-TYPE
	SYNTAX INTEGER
	ACCESS read-only
	STATUS mandatory
	DESCRIPTION
		"The slot number of this port's module."
	::= { ennMSTELCOPortEntry 1 }


ennMSTELCOPortIndex OBJECT-TYPE
	SYNTAX INTEGER
	ACCESS read-only
	STATUS mandatory
	DESCRIPTION
		"The port number of this port."
	::= { ennMSTELCOPortEntry 2 }

ennMSTELCOPortAdminState OBJECT-TYPE
	SYNTAX INTEGER {
		enabled(1),
		disabled(2),
		redundant-primary(3),
		redundant-backup(4),
		remote-diagnostics(8)
		}
	ACCESS read-write
	STATUS mandatory
	DESCRIPTION
		"The desired state of this port.  Setting this port to
		be redundant or for remote diagnostics with invalid settings
		of buddy slot and buddy port will return the genError error."
	::= { ennMSTELCOPortEntry 3 }

ennMSTELCOPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port.

		If the port is configured for remote diagnostics, then
		this contains the slot index of the backup buddy port.
		To configure a port for remote diagnostics, the buddy's
		slot and port must be set to valid values."
	::= { ennMSTELCOPortEntry 4 }

ennMSTELCOPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port.

		If the port is configured for remote diagnostics, then
		this contains the port index of the backup buddy port.
		To configure a port for remote diagnostics, the buddy's
		slot and port must be set to valid values."
	::= { ennMSTELCOPortEntry 5 }

ennMSTELCOPortDipAdminState OBJECT-TYPE
	SYNTAX INTEGER {
		enabled(1),
		disabled(2)
		}
	ACCESS read-only
	STATUS mandatory
	DESCRIPTION
		"The state of this port as indicated by the port's dip
		switches."
	::= { ennMSTELCOPortEntry 6 }

ennMSTELCOPortLinkInteg OBJECT-TYPE
	SYNTAX INTEGER {
		enabled(1),
		disabled(2)
		}
	ACCESS read-write
	STATUS mandatory
	DESCRIPTION
		"The current link integrity configuration for this port."
	::= { ennMSTELCOPortEntry 7 }

ennMSTELCOPortDipLinkInteg OBJECT-TYPE
	SYNTAX INTEGER {
		enabled(1),
		disabled(2)
		}
	ACCESS read-only
	STATUS mandatory
	DESCRIPTION
		"The link integrity configuration as indicated by this
		module's dip switches."
	::= { ennMSTELCOPortEntry 8 }

ennMSTELCOPortSquelch OBJECT-TYPE
	SYNTAX INTEGER {
		normal(1), -- high squelch
		low(2)
		}
	ACCESS read-write
	STATUS mandatory
	DESCRIPTION
		"The current squelch configuration for this port.  See
		the module's user's guide for more information."
	::= { ennMSTELCOPortEntry 9 }

ennMSTELCOPortJabber OBJECT-TYPE
	SYNTAX INTEGER {
		enabled(1),
		disabled(2)
		}
	ACCESS read-write
	STATUS mandatory
	DESCRIPTION
		"The current receive jabber configuration for this port."
	::= { ennMSTELCOPortEntry 10 }

ennMSTELCOPortDipJabber OBJECT-TYPE
	SYNTAX INTEGER {
		enabled(1),
		disabled(2)
		}
	ACCESS read-only
	STATUS mandatory
	DESCRIPTION
		"The receive jabber configuration as indicated by this
		module's dip switches."
	::= { ennMSTELCOPortEntry 11 }


--
-- Ethernet 10BASE-T Per-Port Module
--

ennPSTELCOModTable OBJECT-TYPE
	SYNTAX SEQUENCE OF EnnPSTELCOModEntry
	ACCESS not-accessible
	STATUS mandatory
	DESCRIPTION
		"A list of module-specific information about a specific
		ennPS-TELCO module in the concentrator."
	::= { ennPSTELCO 1 }

ennPSTELCOModEntry OBJECT-TYPE
	SYNTAX EnnPSTELCOModEntry
	ACCESS not-accessible
	STATUS mandatory
	DESCRIPTION
		"A list of module-specific information about a specific
		ennPS-TELCO module in the concentrator."
	INDEX { ennPSTELCOModSlotIndex }
	::= { ennPSTELCOModTable 1 }

EnnPSTELCOModEntry ::=
	SEQUENCE {
		ennPSTELCOModSlotIndex
			INTEGER
		}

ennPSTELCOModSlotIndex OBJECT-TYPE
	SYNTAX INTEGER
	ACCESS read-only
	STATUS mandatory
	DESCRIPTION
		"The slot number of this module."
	::= { ennPSTELCOModEntry 1 }

ennPSTELCOPortTable			 OBJECT-TYPE
	SYNTAX SEQUENCE OF EnnPSTELCOPortEntry
	ACCESS not-accessible
	STATUS mandatory
	DESCRIPTION
		"A table of port-specific information for each port of
		this module type."
	::= { ennPSTELCO 2 }

ennPSTELCOPortEntry OBJECT-TYPE
	SYNTAX EnnPSTELCOPortEntry
	ACCESS not-accessible
	STATUS mandatory
	DESCRIPTION
		"A list of module-specific information about a specific
		ennPS-TELCO port in the concentrator."
	INDEX { ennPSTELCOPortSlotIndex, ennPSTELCOPortIndex }
	::= { ennPSTELCOPortTable 1 }

EnnPSTELCOPortEntry ::=
	SEQUENCE {
		ennPSTELCOPortSlotIndex
			INTEGER,
		ennPSTELCOPortIndex
			INTEGER,
		ennPSTELCOPortAdminState
			INTEGER,
		ennPSTELCOPortBuddySlot
			INTEGER,
		ennPSTELCOPortBuddyPort
			INTEGER,
		ennPSTELCOPortDipAdminState
			INTEGER,
		ennPSTELCOPortDipNetwork
			INTEGER,
		ennPSTELCOPortLinkInteg
			INTEGER,
		ennPSTELCOPortDipLinkInteg
			INTEGER,
		ennPSTELCOPortSquelch
			INTEGER,
		ennPSTELCOPortJabber
			INTEGER,
		ennPSTELCOPortDipJabber
			INTEGER
		}

ennPSTELCOPortSlotIndex OBJECT-TYPE
	SYNTAX INTEGER
	ACCESS read-only
	STATUS mandatory
	DESCRIPTION
		"The slot number of this port's module."
	::= { ennPSTELCOPortEntry 1 }


ennPSTELCOPortIndex OBJECT-TYPE
	SYNTAX INTEGER
	ACCESS read-only
	STATUS mandatory
	DESCRIPTION
		"The port number of this port."
	::= { ennPSTELCOPortEntry 2 }

ennPSTELCOPortAdminState OBJECT-TYPE
	SYNTAX INTEGER {
		enabled(1),
		disabled(2),
		redundant-primary(3),
		redundant-backup(4),
		remote-diagnostics(8)
		}
	ACCESS read-write
	STATUS mandatory
	DESCRIPTION
		"The desired state of this port.  Setting this port to
		be redundant or for remote diagnostics with invalid settings
		of buddy slot and buddy port will return the genError error."
	::= { ennPSTELCOPortEntry 3 }

ennPSTELCOPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port.

		If the port is configured for remote diagnostics, then
		this contains the slot index of the backup buddy port.
		To configure a port for remote diagnostics, the buddy's
		slot and port must be set to valid values."

	::= { ennPSTELCOPortEntry 4 }

ennPSTELCOPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port.

		If the port is configured for remote diagnostics, then
		this contains the port index of the backup buddy port.
		To configure a port for remote diagnostics, the buddy's
		slot and port must be set to valid values."
	::= { ennPSTELCOPortEntry 5 }

ennPSTELCOPortDipAdminState OBJECT-TYPE
	SYNTAX INTEGER {
		enabled(1),
		disabled(2)
		}
	ACCESS read-only
	STATUS mandatory
	DESCRIPTION
		"The state of this port as indicated by the port's dip
		switches."
	::= { ennPSTELCOPortEntry 6 }

ennPSTELCOPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ennPSTELCOPortEntry 7 }

ennPSTELCOPortLinkInteg OBJECT-TYPE
	SYNTAX INTEGER {
		enabled(1),
		disabled(2)
		}
	ACCESS read-write
	STATUS mandatory
	DESCRIPTION
		"The current link integrity configuration for this port."
	::= { ennPSTELCOPortEntry 8 }

ennPSTELCOPortDipLinkInteg OBJECT-TYPE
	SYNTAX INTEGER {
		enabled(1),
		disabled(2)
		}
	ACCESS read-only
	STATUS mandatory
	DESCRIPTION
		"The link integrity configuration as indicated by this
		module's dip switches."
	::= { ennPSTELCOPortEntry 9 }

ennPSTELCOPortSquelch OBJECT-TYPE
	SYNTAX INTEGER {
		normal(1), -- high squelch
		low(2)
		}
	ACCESS read-write
	STATUS mandatory
	DESCRIPTION
		"The current squelch configuration for this port.  See
		the module's user's guide for more information."
	::= { ennPSTELCOPortEntry 10 }

ennPSTELCOPortJabber OBJECT-TYPE
	SYNTAX INTEGER {
		enabled(1),
		disabled(2)
		}
	ACCESS read-write
	STATUS mandatory
	DESCRIPTION
		"The current receive jabber configuration for this port."
	::= { ennPSTELCOPortEntry 11 }

ennPSTELCOPortDipJabber OBJECT-TYPE
	SYNTAX INTEGER {
		enabled(1),
		disabled(2)
		}
	ACCESS read-only
	STATUS mandatory
	DESCRIPTION
		"The receive jabber configuration as indicated by this
		module's dip switches."
	::= { ennPSTELCOPortEntry 12 }

--
-- Token Ring Media Module
--
tnnMSRJ45SModTable OBJECT-TYPE
	SYNTAX SEQUENCE OF TnnMSRJ45SModEntry
	ACCESS not-accessible
	STATUS mandatory
	DESCRIPTION
		"A list of module-specific information about a specific
		tnnMS-RJ45S module in the concentrator."
	::= { tnnMSRJ45S 1 }

tnnMSRJ45SModEntry OBJECT-TYPE
	SYNTAX TnnMSRJ45SModEntry
	ACCESS not-accessible
	STATUS mandatory
	DESCRIPTION
		"A description of the tnnMS-RJ45S module attributes."
	INDEX { tnnMSRJ45SModSlotIndex }
	::= { tnnMSRJ45SModTable 1 }

TnnMSRJ45SModEntry ::=
	SEQUENCE {
		tnnMSRJ45SModSlotIndex
			INTEGER,
		tnnMSRJ45SModRingSpeed
			INTEGER,
		tnnMSRJ45SModDipRingSpeed
			INTEGER,
		tnnMSRJ45SModCableImp
			INTEGER,
		tnnMSRJ45SModDipCableImp
			INTEGER
		}

tnnMSRJ45SModSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		modSlotIndex."
	::= { tnnMSRJ45SModEntry 1 }

tnnMSRJ45SModRingSpeed OBJECT-TYPE
	SYNTAX INTEGER {
		fourMegabit(1),
		sixteenMegabit(2)
		}
	ACCESS read-write
	STATUS mandatory
	DESCRIPTION
		"The ring's bandwidth."
	::= { tnnMSRJ45SModEntry 2 }

tnnMSRJ45SModDipRingSpeed OBJECT-TYPE
	SYNTAX INTEGER {
		fourMegabit(1),
		sixteenMegabit(2)
		}
	ACCESS read-only
	STATUS mandatory
	DESCRIPTION
		"The dip switch setting for the ring's bandwidth."
	::= { tnnMSRJ45SModEntry 3 }

tnnMSRJ45SModCableImp OBJECT-TYPE
	SYNTAX INTEGER {
		ohm100(1),
		ohm150(2)
		}
	ACCESS read-write
	STATUS mandatory
	DESCRIPTION
		"The setting of this module's port impedance matching, with
		100 ohm corresponding to unshielded twisted pair cabling and
		150 ohm corresponding to shielded twisted pair cabling.
		This setting is valid for all ports on this module."
	::= { tnnMSRJ45SModEntry 4 }

tnnMSRJ45SModDipCableImp OBJECT-TYPE
	SYNTAX INTEGER {
		ohm100(1),
		ohm150(2)
		}
	ACCESS read-only
	STATUS mandatory
	DESCRIPTION
		"The dip switch setting for the module's port impedance
		matching."
	::= { tnnMSRJ45SModEntry 5 }

tnnMSRJ45SPortTable OBJECT-TYPE
	SYNTAX SEQUENCE OF TnnMSRJ45SPortEntry
	ACCESS not-accessible
	STATUS mandatory
	DESCRIPTION
		"A table of port-specific information for each port of
		this module type."
	::= { tnnMSRJ45S 2 }

tnnMSRJ45SPortEntry OBJECT-TYPE
	SYNTAX TnnMSRJ45SPortEntry
	ACCESS not-accessible
	STATUS mandatory
	DESCRIPTION
		"A description of tnnMS-RJ45S port attributes."
	INDEX { tnnMSRJ45SPortSlotIndex, tnnMSRJ45SPortIndex }
	::= { tnnMSRJ45SPortTable 1 }

TnnMSRJ45SPortEntry ::=
	SEQUENCE {
		tnnMSRJ45SPortSlotIndex
			INTEGER,
		tnnMSRJ45SPortIndex
			INTEGER,
		tnnMSRJ45SPortDipAdminState
			INTEGER,
		tnnMSRJ45SPortStationType
			INTEGER
		}

tnnMSRJ45SPortSlotIndex OBJECT-TYPE
	SYNTAX INTEGER
	ACCESS read-only
	STATUS mandatory
	DESCRIPTION
		"The slot number of this port's module."
	::= { tnnMSRJ45SPortEntry 1 }


tnnMSRJ45SPortIndex OBJECT-TYPE
	SYNTAX INTEGER
	ACCESS read-only
	STATUS mandatory
	DESCRIPTION
		"The port number of this port."
	::= { tnnMSRJ45SPortEntry 2 }

tnnMSRJ45SPortDipAdminState OBJECT-TYPE
	SYNTAX INTEGER {
		enabled(1),
		disabled(2)
		}
	ACCESS read-only
	STATUS mandatory
	DESCRIPTION
		"The state of this port as indicated by the port's dip
		switches."
	::= { tnnMSRJ45SPortEntry 3 }

tnnMSRJ45SPortStationType OBJECT-TYPE
	SYNTAX INTEGER {
		mac-present(1),
		mac-not-present(2)
		}
	ACCESS read-write
	STATUS mandatory
	DESCRIPTION
		"Determines whether the station connected to this port
		has a MAC address."
	::= { tnnMSRJ45SPortEntry 4 }

tnnMSRJ45STrunkTable OBJECT-TYPE
	SYNTAX SEQUENCE OF TnnMSRJ45STrunkEntry
	ACCESS not-accessible
	STATUS mandatory
	DESCRIPTION
		"A list of trunk-specific information about each trunk
		for this module type."
	::= { tnnMSRJ45S 3 }

tnnMSRJ45STrunkEntry OBJECT-TYPE
	SYNTAX TnnMSRJ45STrunkEntry
	ACCESS not-accessible
	STATUS mandatory
	DESCRIPTION
		"A description of tnnMS-RJ45S trunk attributes."
	INDEX { tnnMSRJ45STrunkSlotIndex, tnnMSRJ45STrunkIndex }
	::= { tnnMSRJ45STrunkTable 1 }

TnnMSRJ45STrunkEntry ::=
	SEQUENCE {
		tnnMSRJ45STrunkSlotIndex
			INTEGER,
		tnnMSRJ45STrunkIndex
			INTEGER,
		tnnMSRJ45STrunkDipAdminState
			INTEGER
		}

tnnMSRJ45STrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { tnnMSRJ45STrunkEntry 1 }


tnnMSRJ45STrunkIndex OBJECT-TYPE
	SYNTAX INTEGER
	ACCESS read-only
	STATUS mandatory
	DESCRIPTION
		"The trunk number for this trunk."
	::= { tnnMSRJ45STrunkEntry 2 }

tnnMSRJ45STrunkDipAdminState OBJECT-TYPE
	SYNTAX INTEGER {
		enabled(1),
		disabled(2)
		}
	ACCESS read-only
	STATUS mandatory
	DESCRIPTION
		"The state of this trunk as indicated by the trunk's dip
		switches."
	::= { tnnMSRJ45STrunkEntry 3 }

--
-- Token Fiberoptic Repeater Module
--
tnnMSFIBModTable OBJECT-TYPE
	SYNTAX SEQUENCE OF TnnMSFIBModEntry
	ACCESS not-accessible
	STATUS mandatory
	DESCRIPTION
		"A list of module-specific information about a specific
		tnnMS-FIB module in the concentrator."
	::= { tnnMSFIB 1 }

tnnMSFIBModEntry OBJECT-TYPE
	SYNTAX TnnMSFIBModEntry
	ACCESS not-accessible
	STATUS mandatory
	DESCRIPTION
		"A description of the tnnMS-FIB module attributes."
	INDEX { tnnMSFIBModSlotIndex }
	::= { tnnMSFIBModTable 1 }

TnnMSFIBModEntry ::=
	SEQUENCE {
		tnnMSFIBModSlotIndex
			INTEGER,
		tnnMSFIBModRingSpeed
			INTEGER,
		tnnMSFIBModDipRingSpeed
			INTEGER
		}

tnnMSFIBModSlotIndex OBJECT-TYPE
	SYNTAX INTEGER
	ACCESS read-only
	STATUS mandatory
	DESCRIPTION
		"The slot number of this module."
	::= { tnnMSFIBModEntry 1 }

tnnMSFIBModRingSpeed OBJECT-TYPE
	SYNTAX INTEGER {
		fourMegabit(1),
		sixteenMegabit(2)
		}
	ACCESS read-write
	STATUS mandatory
	DESCRIPTION
		"The ring's bandwidth."
	::= { tnnMSFIBModEntry 2 }

tnnMSFIBModDipRingSpeed OBJECT-TYPE
	SYNTAX INTEGER {
		fourMegabit(1),
		sixteenMegabit(2)
		}
	ACCESS read-only
	STATUS mandatory
	DESCRIPTION
		"The dip switch setting for the ring's bandwidth."
	::= { tnnMSFIBModEntry 3 }

tnnMSFIBPortTable OBJECT-TYPE
	SYNTAX SEQUENCE OF TnnMSFIBPortEntry
	ACCESS not-accessible
	STATUS mandatory
	DESCRIPTION
		"A table of port-specific information for each port of
		this module type."
	::= { tnnMSFIB 2 }

tnnMSFIBPortEntry OBJECT-TYPE
	SYNTAX TnnMSFIBPortEntry
	ACCESS not-accessible
	STATUS mandatory
	DESCRIPTION
		"A description of tnnMS-FIB port attributes."
	INDEX { tnnMSFIBPortSlotIndex, tnnMSFIBPortIndex }
	::= { tnnMSFIBPortTable 1 }

TnnMSFIBPortEntry ::=
	SEQUENCE {
		tnnMSFIBPortSlotIndex
			INTEGER,
		tnnMSFIBPortIndex
			INTEGER,
		tnnMSFIBPortDipAdminState
			INTEGER,
		tnnMSFIBPortCableImp
			INTEGER,
		tnnMSFIBPortStationType
			INTEGER
		}

tnnMSFIBPortSlotIndex OBJECT-TYPE
	SYNTAX INTEGER
	ACCESS read-only
	STATUS mandatory
	DESCRIPTION
		"The slot number of this port's module."
	::= { tnnMSFIBPortEntry 1 }


tnnMSFIBPortIndex OBJECT-TYPE
	SYNTAX INTEGER
	ACCESS read-only
	STATUS mandatory
	DESCRIPTION
		"The port number of this port."
	::= { tnnMSFIBPortEntry 2 }

tnnMSFIBPortDipAdminState OBJECT-TYPE
	SYNTAX INTEGER {
		enabled(1),
		disabled(2)
		}
	ACCESS read-only
	STATUS mandatory
	DESCRIPTION
		"The state of this port as indicated by the port's dip
		switches."
	::= { tnnMSFIBPortEntry 3 }

tnnMSFIBPortCableImp OBJECT-TYPE
	SYNTAX INTEGER {
		ohm100(1),
		ohm150(2)
		}
	ACCESS read-only
	STATUS mandatory
	DESCRIPTION
		"The setting of this port's impedance matching, with 100 ohm
		corresponding to unshielded twisted pair cabling and 150 ohm
		corresponding to shielded twisted pair cabling."
	::= { tnnMSFIBPortEntry 4 }

tnnMSFIBPortStationType OBJECT-TYPE
	SYNTAX INTEGER {
		mac-present(1),
		mac-not-present(2)
		}
	ACCESS read-write
	STATUS mandatory
	DESCRIPTION
		"Determines whether the station connected to this port
		has a MAC address."
	::= { tnnMSFIBPortEntry 5 }

tnnMSFIBTrunkTable OBJECT-TYPE
	SYNTAX SEQUENCE OF TnnMSFIBTrunkEntry
	ACCESS not-accessible
	STATUS mandatory
	DESCRIPTION
		"A list of trunk-specific information about each trunk
		for this module type."
	::= { tnnMSFIB 3 }

tnnMSFIBTrunkEntry OBJECT-TYPE
	SYNTAX TnnMSFIBTrunkEntry
	ACCESS not-accessible
	STATUS mandatory
	DESCRIPTION
		"A description of tnnMS-FIB trunk attributes."
	INDEX { tnnMSFIBTrunkSlotIndex, tnnMSFIBTrunkIndex }
	::= { tnnMSFIBTrunkTable 1 }

TnnMSFIBTrunkEntry ::=
	SEQUENCE {
		tnnMSFIBTrunkSlotIndex
			INTEGER,
		tnnMSFIBTrunkIndex
			INTEGER,
		tnnMSFIBTrunkDipAdminState
			INTEGER,
		tnnMSFIBTrunkCableMon
			INTEGER,
		tnnMSFIBTrunkDipCableMon
			INTEGER,
		tnnMSFIBTrunkCompMode
			INTEGER,
		tnnMSFIBTrunkDipCompMode
			INTEGER,
		tnnMSFIBTrunkNetMapState
			INTEGER,
		tnnMSFIBTrunkExtBcnRecovery
			INTEGER

		}

tnnMSFIBTrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { tnnMSFIBTrunkEntry 1 }


tnnMSFIBTrunkIndex OBJECT-TYPE
	SYNTAX INTEGER
	ACCESS read-only
	STATUS mandatory
	DESCRIPTION
		"The trunk number of this trunk."
	::= { tnnMSFIBTrunkEntry 2 }

tnnMSFIBTrunkDipAdminState OBJECT-TYPE
	SYNTAX INTEGER {
		enabled(1),
		disabled(2)
		}
	ACCESS read-only
	STATUS mandatory
	DESCRIPTION
		"The state of this trunk as indicated by the trunk's dip
		switches."
	::= { tnnMSFIBTrunkEntry 3 }

tnnMSFIBTrunkCableMon OBJECT-TYPE
	SYNTAX INTEGER {
		enabled(1),
		disabled(2),
		notApplicable(3)
	}
	ACCESS read-write
	STATUS mandatory
	DESCRIPTION
		"The cable monitor configuration for this trunk. This
		does not apply to fiber trunks."
	::= { tnnMSFIBTrunkEntry 4 }

tnnMSFIBTrunkDipCableMon OBJECT-TYPE
	SYNTAX INTEGER {
		enabled(1),
		disabled(2),
		notApplicable(3)
	}
	ACCESS read-only
	STATUS mandatory
	DESCRIPTION
		"The cable monitor configuration as indicated by this trunk's
		dip switches. This does not apply to fiber trunks."
	::= { tnnMSFIBTrunkEntry 5 }


tnnMSFIBTrunkCompMode OBJECT-TYPE
	SYNTAX INTEGER {
		enabled(1),
		disabled(2),
		notApplicable(3)
	}
	ACCESS read-write
	STATUS mandatory
	DESCRIPTION
		"The compatibility mode for this trunk. This
		only applies to fiber trunks."
	::= { tnnMSFIBTrunkEntry 6 }

tnnMSFIBTrunkDipCompMode OBJECT-TYPE
	SYNTAX INTEGER {
		enabled(1),
		disabled(2),
		notApplicable(3)
	}
	ACCESS read-only
	STATUS mandatory
	DESCRIPTION
		"The compatibility mode as indicated by this trunk's
		dip switches. This only applies to fiber trunks."
	::= { tnnMSFIBTrunkEntry 7 }


tnnMSFIBTrunkNetMapState OBJECT-TYPE
	SYNTAX INTEGER {
		notApplicable(1),
		internal(2),
		external(3)
	}
	ACCESS read-write
	STATUS mandatory
	DESCRIPTION
		"The map state of the copper ring-in trunk.  This
		should be set to external for ring-in trunks which
		connect to external hubs.  The mapping logic will not
		operate on trunks which are set to external.  This
		prevents incorrect mapping which can occur when a
		module in one hub detects the mapping signal from
		another hub. This attribute only applies to copper
		ring-in trunks."
	::= { tnnMSFIBTrunkEntry 8 }


tnnMSFIBTrunkExtBcnRecovery OBJECT-TYPE
	SYNTAX INTEGER {
		exists(1),
		nonExists(2),
		notApplicable(3)
	}
	ACCESS read-write
	STATUS mandatory
	DESCRIPTION
		"Indicates whether the trunk is connected to a
		segment that will perform beacon recovery.  This
		should be set to exists(1) for trunks which connect
		to hubs which perform beacon recovery.  This attribute
		is used to determine the fault domain when resolving a
		beaconing condition.

		The beacon recovery process will resolve beaconing on
		trunks with this attribute set to nonExists(2) before
		trunks with the attribute set to exists(1) are resolved.
		For backplane trunks, setting to a value other than
		notApplicable will return invalidData error.  The
		default value is nonExists(2)."
	::= { tnnMSFIBTrunkEntry 9 }



--
-- Ethernet Terminal Server Module
--


ennMSTSModTable OBJECT-TYPE
	SYNTAX SEQUENCE OF EnnMSTSModEntry
	ACCESS not-accessible
	STATUS mandatory
	DESCRIPTION
		"A table of module-specific information for each
		ennMS-TS module in the concentrator."
	::= { ennMSTS 1 }

ennMSTSModEntry OBJECT-TYPE
       SYNTAX EnnMSTSModEntry
       ACCESS not-accessible
       STATUS mandatory
       DESCRIPTION
	       "A list of module information for each ennMS-TS module
	       in the concentrator."
       INDEX { ennMSTSModSlotIndex }
       ::= { ennMSTSModTable 1 }

EnnMSTSModEntry ::=
       SEQUENCE {
	       ennMSTSModSlotIndex
		       INTEGER,
	       ennMSTSModProtocols
		       DisplayString,
	       ennMSTSModIpAddress
		       IpAddress,
	       ennMSTSModTCPPort
		       INTEGER,
	       ennMSTSModStationAddr
		       OCTET STRING,
	       ennMSTSModDipNetwork
		       INTEGER,
	       ennMSTSModCPURev
		       DisplayString
	       }

ennMSTSModSlotIndex OBJECT-TYPE
       SYNTAX INTEGER
       ACCESS read-only
       STATUS mandatory
       DESCRIPTION
	       "The slot number of this module."
       ::= { ennMSTSModEntry 1 }

ennMSTSModProtocols OBJECT-TYPE
	SYNTAX DisplayString
	ACCESS read-only
	STATUS mandatory
	DESCRIPTION
		"A textual description of the protocols supported by
		this module"
	::= { ennMSTSModEntry 2 }

ennMSTSModIpAddress OBJECT-TYPE
       SYNTAX IpAddress
       ACCESS read-only
       STATUS mandatory
       DESCRIPTION
	       "The IP Address of the terminal server."
       ::= { ennMSTSModEntry 3 }

ennMSTSModTCPPort OBJECT-TYPE
       SYNTAX INTEGER
       ACCESS read-only
       STATUS mandatory
       DESCRIPTION
	       "The TCP port number of the the terminal server's remote
		console port."
       ::= { ennMSTSModEntry 4 }

ennMSTSModStationAddr OBJECT-TYPE
       SYNTAX OCTET STRING (SIZE(6))
       ACCESS read-only
       STATUS mandatory
       DESCRIPTION
	       "A 6 octet address that uniquely identifies this module.
	       The station address is the mac address of the terminal server."
       ::= { ennMSTSModEntry 5 }

ennMSTSModDipNetwork OBJECT-TYPE
       SYNTAX INTEGER {
	       isolated(2),
	       ethernet-1(6),
	       ethernet-2(7),
	       ethernet-3(8)
	       }
       ACCESS read-only
       STATUS mandatory
       DESCRIPTION
	       "The network indicated by the module's dip switches."
       ::= { ennMSTSModEntry 6 }

ennMSTSModCPURev OBJECT-TYPE
       SYNTAX DisplayString (SIZE(1..10))
       ACCESS read-only
       STATUS mandatory
       DESCRIPTION
	       "The terminal server's CPU revision."
       ::= { ennMSTSModEntry 7 }


ennMSTSPortTable OBJECT-TYPE
       SYNTAX SEQUENCE OF EnnMSTSPortEntry
       ACCESS not-accessible
       STATUS mandatory
       DESCRIPTION
	       "A table of information that contains port-specific
	       information for each port on each ennMS-TS module."
       ::= { ennMSTS 2 }

ennMSTSPortEntry OBJECT-TYPE
       SYNTAX EnnMSTSPortEntry
       ACCESS not-accessible
       STATUS mandatory
       DESCRIPTION
	       "A list of information about a specific port on a
	       ennMS-TS module."
       INDEX { ennMSTSPortSlotIndex, ennMSTSPortIndex }
       ::= { ennMSTSPortTable 1 }

EnnMSTSPortEntry ::=
       SEQUENCE {
	       ennMSTSPortSlotIndex
		       INTEGER,
	       ennMSTSPortIndex
		       INTEGER,
	       ennMSTSPortAdminState
		       INTEGER,
	       ennMSTSPortOperState
		       INTEGER
	       }

ennMSTSPortSlotIndex OBJECT-TYPE
       SYNTAX INTEGER
       ACCESS read-only
       STATUS mandatory
       DESCRIPTION
		"The slot number for this port."
       ::= { ennMSTSPortEntry 1 }

ennMSTSPortIndex OBJECT-TYPE
       SYNTAX INTEGER
       ACCESS read-only
       STATUS mandatory
       DESCRIPTION
		"The port number of this port."
       ::= { ennMSTSPortEntry 2 }

ennMSTSPortAdminState OBJECT-TYPE
       SYNTAX INTEGER {
	       enabled(1),
	       disabled(2),
	       local(6),
	       remote(7)
	       }
       ACCESS read-write
       STATUS mandatory
       DESCRIPTION
	       "The administrative state of this port."
       ::= { ennMSTSPortEntry 3 }

ennMSTSPortOperState OBJECT-TYPE
       SYNTAX INTEGER {
	       idle(1),
	       local(2),
	       connected(3)
	       }
       ACCESS read-only
       STATUS mandatory
       DESCRIPTION
	       "The operational mode of this port."
       ::= { ennMSTSPortEntry 4 }


--
-- Ethernet FOIRL MOdule
--


ennMSFOIRLModTable OBJECT-TYPE
	SYNTAX SEQUENCE OF EnnMSFOIRLModEntry
	ACCESS not-accessible
	STATUS mandatory
	DESCRIPTION
		"A table of module-specific information for each
		ennMS-FOIRL module in the concentrator."
	::= { ennMSFOIRL 1 }

ennMSFOIRLModEntry OBJECT-TYPE
	SYNTAX EnnMSFOIRLModEntry
	ACCESS not-accessible
	STATUS mandatory
	DESCRIPTION
		"A list of module-specific information associated
		with a particular ennMS-FOIRL module in the concentrator."
	INDEX { ennMSFOIRLModSlotIndex }
	::= { ennMSFOIRLModTable 1 }

EnnMSFOIRLModEntry ::=
	SEQUENCE {
		ennMSFOIRLModSlotIndex
			INTEGER,
		ennMSFOIRLModDipNetwork
			INTEGER
		}

ennMSFOIRLModSlotIndex OBJECT-TYPE
	SYNTAX INTEGER
	ACCESS read-only
	STATUS mandatory
	DESCRIPTION
		"The slot number of this module."
	::= { ennMSFOIRLModEntry 1 }

ennMSFOIRLModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSFOIRLModEntry 2 }

ennMSFOIRLPortTable OBJECT-TYPE
	SYNTAX SEQUENCE OF EnnMSFOIRLPortEntry
	ACCESS not-accessible
	STATUS mandatory
	DESCRIPTION
		"A table of port-specific information for each port
		of each ennMS-FOIRL module."
	::= { ennMSFOIRL 2 }

ennMSFOIRLPortEntry OBJECT-TYPE
	SYNTAX EnnMSFOIRLPortEntry
	ACCESS not-accessible
	STATUS mandatory
	DESCRIPTION
		"A list of information about a specific port on a
		ennMS-FOIRL module."
	INDEX { ennMSFOIRLPortSlotIndex, ennMSFOIRLPortIndex }
	::= { ennMSFOIRLPortTable 1 }

EnnMSFOIRLPortEntry ::=
	SEQUENCE {
		ennMSFOIRLPortSlotIndex
			INTEGER,
		ennMSFOIRLPortIndex
			INTEGER,
		ennMSFOIRLPortAdminState
			INTEGER,
		ennMSFOIRLPortBuddySlot
			INTEGER,
		ennMSFOIRLPortBuddyPort
			INTEGER,
		ennMSFOIRLPortDipAdminState
			INTEGER
		}

	ennMSFOIRLPortSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		portSlotIndex."
	::= { ennMSFOIRLPortEntry 1 }


ennMSFOIRLPortIndex OBJECT-TYPE
	SYNTAX INTEGER
	ACCESS read-only
	STATUS mandatory
	DESCRIPTION
		"The port number of this port."
	::= { ennMSFOIRLPortEntry 2 }


ennMSFOIRLPortAdminState OBJECT-TYPE
	SYNTAX INTEGER {
		enabled(1),
		disabled(2),
		redundant-primary(3),
		redundant-backup(4),
		redundant-rfs(5)
		}
	ACCESS read-write
	STATUS mandatory
	DESCRIPTION
		"The desired state of this port.  Setting this port to
		be redundant with invalid settings of buddy slot and
		buddy port will return invalidData error. Remote
		Failure Signaling (RFS), is set on connected module
		port to permit transmit error detection on local port.
		Port must be set to be RFS when connected port is set to
		be redundant"
	::= { ennMSFOIRLPortEntry 3 }

ennMSFOIRLPortBuddySlot OBJECT-TYPE
	SYNTAX INTEGER
	ACCESS read-write
	STATUS mandatory
	DESCRIPTION
		"The slot index of the redundant port's buddy.   "
	::= { ennMSFOIRLPortEntry 4 }


ennMSFOIRLPortBuddyPort  OBJECT-TYPE
	SYNTAX INTEGER
	ACCESS read-write
	STATUS mandatory
	DESCRIPTION
		"The port index of the redundant port's buddy."
	::= { ennMSFOIRLPortEntry 5 }


ennMSFOIRLPortDipAdminState OBJECT-TYPE
	SYNTAX INTEGER {
		enabled(1),
		disabled(2),
		redundant-primary(3),
		redundant-backup(4),
		redundant-rfs(5)
		}
	ACCESS read-only
	STATUS mandatory
	DESCRIPTION
		"The state of this port as indicated by the port's dip
		switches."
	::= { ennMSFOIRLPortEntry 6 }


--
-- Hub Redundant Controller Module
--

cnnNSRCTLModTable OBJECT-TYPE
	SYNTAX SEQUENCE OF CnnNSRCTLModEntry
	ACCESS not-accessible
	STATUS mandatory
	DESCRIPTION
		"A table that contains information about each cnnNS-RCTL
		in the concentrator.  "
	::= { cnnNSRCTL 1 }

cnnNSRCTLModEntry OBJECT-TYPE
	SYNTAX CnnNSRCTLModEntry
	ACCESS not-accessible
	STATUS mandatory
	DESCRIPTION
		"A list of information for each cnnNS-RCTL module
		in the concentrator."
	INDEX { cnnNSRCTLModSlotIndex }
	::= { cnnNSRCTLModTable 1 }

CnnNSRCTLModEntry ::=
	SEQUENCE {
		cnnNSRCTLModSlotIndex
			INTEGER,
		cnnNSRCTLModOperState
			INTEGER,
		cnnNSRCTLModClockStatus
			INTEGER,
		cnnNSRCTLModTempStatus
			INTEGER
		}

cnnNSRCTLModSlotIndex OBJECT-TYPE
	SYNTAX INTEGER
	ACCESS read-only
	STATUS mandatory
	DESCRIPTION
		"The slot number for this module."
	::= { cnnNSRCTLModEntry 1 }

cnnNSRCTLModOperState OBJECT-TYPE
	SYNTAX INTEGER {
		active(1),
		standby(2)
		}
	ACCESS read-only
	STATUS mandatory
	DESCRIPTION
		"The operational state of the cnnNS-RCTL module.  Specifically,
		this is an indicator of whether the cnnNS-RCTL module is
		providing clock signals to the backplane.  An active cnnNS-RCTL
		module provides clock signals to the backplane while a standby
		cnnNS-RCTL module does not.  Note that only one cnnNS-RCTL
		module will be active at any given time; all other cnnNS-RCTL
		modules in the concentrator will be in standby mode."
	::= { cnnNSRCTLModEntry 2 }

cnnNSRCTLModClockStatus OBJECT-TYPE
	SYNTAX INTEGER {
		okay(1),
		faulty(2)
		}
	ACCESS read-only
	STATUS mandatory
	DESCRIPTION
		"The current status of the on-board clocks on this module."
	::= { cnnNSRCTLModEntry 3 }

cnnNSRCTLModTempStatus OBJECT-TYPE
	SYNTAX INTEGER {
		okay(1),
		extremeTemp(2)
		}
	ACCESS read-only
	STATUS mandatory
	DESCRIPTION
		"The temperature as detected by the probe on this module."
	::= { cnnNSRCTLModEntry 4 }

--
-- Ethernet 10BASE-F Module
--

ennMSFBModTable OBJECT-TYPE
	SYNTAX SEQUENCE OF EnnMSFBModEntry
	ACCESS not-accessible
	STATUS mandatory
	DESCRIPTION
		"A list of module-specific information associated
		with a particular ennPS-FB module in the concentrator."
	::= { ennMSFB 1 }

ennMSFBModEntry OBJECT-TYPE
	SYNTAX EnnMSFBModEntry
	ACCESS not-accessible
	STATUS mandatory
	DESCRIPTION
		"A list of module-specific information about a specific
		ennPS-FB module in the concentrator."
	INDEX { ennMSFBModSlotIndex }
	::= { ennMSFBModTable 1 }

EnnMSFBModEntry ::=
	SEQUENCE {
		ennMSFBModSlotIndex
			INTEGER,
		ennMSFBModDipNetwork
			INTEGER,
		ennMSFBModLLW
			INTEGER,
		ennMSFBModDipLLW
			INTEGER
		}

ennMSFBModSlotIndex OBJECT-TYPE
	SYNTAX INTEGER
	ACCESS read-only
	STATUS mandatory
	DESCRIPTION
		"The slot number of this module."
	::= { ennMSFBModEntry 1 }

ennMSFBModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSFBModEntry 2 }

ennMSFBModLLW OBJECT-TYPE
	SYNTAX INTEGER {
		enabled(1),
		disabled(2)
		}
	ACCESS read-write
	STATUS mandatory
	DESCRIPTION
		"The current state of this module's low light warning
		configuration.  Enabling this feature causes the module to
		check for low light and to issue a warning if low light is
		present.  Disabling low light has the advantage of faster
		redundancy switchover in the event of a port error."
	::= { ennMSFBModEntry 3 }

ennMSFBModDipLLW OBJECT-TYPE
	SYNTAX INTEGER {
		enabled(1),
		disabled(2)
		}
	ACCESS read-only
	STATUS mandatory
	DESCRIPTION
		"The low light warning configuration indicated by this module's
		dip switches."
	::= { ennMSFBModEntry 4 }

ennMSFBPortTable OBJECT-TYPE
	SYNTAX SEQUENCE OF EnnMSFBPortEntry
	ACCESS not-accessible
	STATUS mandatory
	DESCRIPTION
		"A table of port-specific information for each port of
		this module type."
	::= { ennMSFB 2 }

ennMSFBPortEntry OBJECT-TYPE
	SYNTAX EnnMSFBPortEntry
	ACCESS not-accessible
	STATUS mandatory
	DESCRIPTION
		"A list of module-specific information about a specific
		ennPS-FB port in the concentrator."
	INDEX { ennMSFBPortSlotIndex, ennMSFBPortIndex }
	::= { ennMSFBPortTable 1 }

EnnMSFBPortEntry ::=
	SEQUENCE {
		ennMSFBPortSlotIndex
			INTEGER,
		ennMSFBPortIndex
			INTEGER,
		ennMSFBPortAdminState
			INTEGER,
		ennMSFBPortBuddySlot
			INTEGER,
		ennMSFBPortBuddyPort
			INTEGER,
		ennMSFBPortDipAdminState
			INTEGER
		}

ennMSFBPortSlotIndex OBJECT-TYPE
	SYNTAX INTEGER
	ACCESS read-only
	STATUS mandatory
	DESCRIPTION
		"The slot number of this port's module."
	::= { ennMSFBPortEntry 1 }


ennMSFBPortIndex OBJECT-TYPE
	SYNTAX INTEGER
	ACCESS read-only
	STATUS mandatory
	DESCRIPTION
		"The port number of this port."
	::= { ennMSFBPortEntry 2 }

ennMSFBPortAdminState OBJECT-TYPE
	SYNTAX INTEGER {
		enabled(1),
		disabled(2),
		redundant-primary(3),
		redundant-backup(4)
		}
	ACCESS read-write
	STATUS mandatory
	DESCRIPTION
		"The desired state of this port.  Setting this port to
		be redundant with invalid settings of buddy slot and
		buddy port will return the genError error."
	::= { ennMSFBPortEntry 3 }

ennMSFBPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port."
	::= { ennMSFBPortEntry 4 }

ennMSFBPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port."
	::= { ennMSFBPortEntry 5 }

ennMSFBPortDipAdminState OBJECT-TYPE
	SYNTAX INTEGER {
		enabled(1),
		disabled(2)
		}
	ACCESS read-only
	STATUS mandatory
	DESCRIPTION
		"The state of this port as indicated by the port's dip
		switches."
	::= { ennMSFBPortEntry 6 }


--
-- FDDI media module, for fiber with MIC connector
--

fnnMSFBMICModTable OBJECT-TYPE
	SYNTAX SEQUENCE OF FnnMSFBMICModEntry
	ACCESS not-accessible
	STATUS mandatory
	DESCRIPTION
		"A list of module attributes that apply to this model.
		To access an fnnMSFBMICModTable entry, the
		fnnMSFBMICModSlotIndex attribute is used."
	::= { fnnMSFBMIC 1 }

fnnMSFBMICModEntry OBJECT-TYPE
	SYNTAX FnnMSFBMICModEntry
	ACCESS not-accessible
	STATUS mandatory
	DESCRIPTION
		"A list of module-specific information about a specific
		fnnMS-FBMIC module in the concentrator."
	INDEX { fnnMSFBMICModSlotIndex }
	::= { fnnMSFBMICModTable 1 }

FnnMSFBMICModEntry ::=
	SEQUENCE {
		fnnMSFBMICModSlotIndex
			INTEGER,
		fnnMSFBMICModDownStreamModule
			INTEGER,
		fnnMSFBMICModUpStreamModule
			INTEGER,
		fnnMSFBMICModDownStreamOperPath
			INTEGER,
		fnnMSFBMICModUpStreamOperPath
			INTEGER,
		fnnMSFBMICModRingInfo
			OCTET STRING
		}

fnnMSFBMICModSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of modSlotIndex."
	::= { fnnMSFBMICModEntry 1 }

fnnMSFBMICModDownStreamModule OBJECT-TYPE
	SYNTAX INTEGER (1..16)
	ACCESS read-only
	STATUS mandatory
	DESCRIPTION
		"Down stream slot (transmit to)"
	::= { fnnMSFBMICModEntry 2 }

fnnMSFBMICModUpStreamModule OBJECT-TYPE
	SYNTAX INTEGER (1..16)
	ACCESS read-only
	STATUS mandatory
	DESCRIPTION
		"Up stream slot (receive from)"
	::= { fnnMSFBMICModEntry 3 }

fnnMSFBMICModDownStreamOperPath OBJECT-TYPE
	SYNTAX INTEGER {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"Transmit DBA  (debug only)"
	::= { fnnMSFBMICModEntry 4 }

fnnMSFBMICModUpStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"Receive DBA (debug only)"
	::= { fnnMSFBMICModEntry 5 }

fnnMSFBMICModRingInfo OBJECT-TYPE
	SYNTAX OCTET STRING (SIZE(1..8))
	ACCESS read-only
	STATUS mandatory
	DESCRIPTION
		"An array which is indexed by DBA number. Each element
		 contains the slot number (1..16) which is assigned to
		 transmit on this DBA. (debug only)"
	::= { fnnMSFBMICModEntry 6 }


-- port table

fnnMSFBMICPortTable OBJECT-TYPE
	SYNTAX SEQUENCE OF FnnMSFBMICPortEntry
	ACCESS not-accessible
	STATUS mandatory
	DESCRIPTION
		"A table of port-specific information for each port of
		this module type."
	::= { fnnMSFBMIC 2 }

fnnMSFBMICPortEntry OBJECT-TYPE
	SYNTAX FnnMSFBMICPortEntry
	ACCESS not-accessible
	STATUS mandatory
	DESCRIPTION
		"A list of module-specific information about a specific
		fnnMS-FBMIC port in the concentrator."
	INDEX { fnnMSFBMICPortSlotIndex, fnnMSFBMICPortIndex }
	::= { fnnMSFBMICPortTable 1 }

FnnMSFBMICPortEntry ::=
	SEQUENCE {
		fnnMSFBMICPortSlotIndex
			INTEGER,
		fnnMSFBMICPortIndex
			INTEGER,
		fnnMSFBMICPortConfig
			INTEGER,
		fnnMSFBMICPortPcmState
			INTEGER,
		fnnMSFBMICPortConnectState
			INTEGER,
		fnnMSFBMICPortNeighbor
			INTEGER,
		fnnMSFBMICPortRemoteMACIndicated
			INTEGER,
		fnnMSFBMICPortBSFlag
			INTEGER,
		fnnMSFBMICPortPCWithhold
			INTEGER,
		fnnMSFBMICPortLerCondition
			INTEGER
		}

fnnMSFBMICPortSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		portSlotIndex."
	::= { fnnMSFBMICPortEntry 1 }


fnnMSFBMICPortIndex OBJECT-TYPE
	SYNTAX INTEGER
	ACCESS read-only
	STATUS mandatory
	DESCRIPTION
		"A unique value that identifies a particular port within this
		module. Its value ranges between 1 and modPortNumber.
		The module identified by a particular value of this index is
		the same module as indentified by the same value of
		portIndex."
	::= { fnnMSFBMICPortEntry 2 }

fnnMSFBMICPortConfig OBJECT-TYPE
	SYNTAX INTEGER {
		slave(3),
		master(4)
		}
	ACCESS read-write
	STATUS mandatory
	DESCRIPTION
		"Specifies the FDDI port type. If the port is on an
		 FFM, the only allowed values are slave(3), and master(4).
		 In addition, there can only be one active slave port on any
		 concentrator FDDI network."
	::= { fnnMSFBMICPortEntry 3 }

fnnMSFBMICPortPcmState OBJECT-TYPE
	SYNTAX INTEGER {
		  pc0(1), -- Off
		  pc1(2), -- Break
		  pc2(3), -- Trace
		  pc3(4), -- Connect
		  pc4(5), -- Next
		  pc5(6), -- Signal
		  pc6(7), -- Join
		  pc7(8), -- Verify
		  pc8(9), -- Active
		  pc9(10) -- Maint
	}
	ACCESS read-only
	STATUS mandatory
	DESCRIPTION
		      "(refer to ANSI SMT 9.6.2)."
	::= { fnnMSFBMICPortEntry 4 }

fnnMSFBMICPortConnectState OBJECT-TYPE
	SYNTAX INTEGER {
	  disabled(1),
	  connecting(2),
	  standby(3),
	  active(4)
		}
	ACCESS read-only
	STATUS mandatory
	DESCRIPTION
	     "An indication of the connect state of this PORT.
	      Basically, this gives a higher level view of the
	      state of the connection by grouping PCM states and
	      the PC-Withhold flag state.  The supported values
	      and their corresponding PCM states and PC-Withhold
	      condition, when relevant, are:
		  disabled: (PC0:Off, PC9:Maint)
		  connecting: (PC1(Break) || PC3 (Connect) || PC4(next) ||
			       PC5 (Signal) || PC6(Join) || PC7 (Verify)) &&
			      (PC_Withhold = None)
		  standby: (PC_Withhold != None)
		  active: (PC2:Trace || PC8:Active)"
	::= { fnnMSFBMICPortEntry 5 }

fnnMSFBMICPortNeighbor OBJECT-TYPE
	SYNTAX INTEGER {
		a(1),
		b(2),
		slave(3),
		master(4),
		unknown(5)
		}
	ACCESS read-only
	STATUS mandatory
	DESCRIPTION
	     "The type (PC_Neighbor) of the remote PORT that is
	      determined in PC_Signaling in R_Val (1,2) (refer
	      to ANSI SMT 9.6.3.2)."
	::= { fnnMSFBMICPortEntry 6 }

fnnMSFBMICPortRemoteMACIndicated OBJECT-TYPE
	SYNTAX INTEGER { true(1), false(2) }
	ACCESS read-only
	STATUS mandatory
	DESCRIPTION
	  "The indication, in PC-Signaling that the remote
	   partner intends to place a MAC in the output token
	   PATH of this PORT.  Signaled as R_Val (9) (refer
	   to ANSI SMT 9.6.3.2)."
	::= { fnnMSFBMICPortEntry 7 }

fnnMSFBMICPortBSFlag OBJECT-TYPE
	SYNTAX INTEGER { true(1), false(2) }
	ACCESS read-only
	STATUS mandatory
	DESCRIPTION
	  "The Break State, BS_Flag (refer to ANSI SMT
	   9.4.3.4)."
	::= { fnnMSFBMICPortEntry 8 }

fnnMSFBMICPortPCWithhold OBJECT-TYPE
	SYNTAX INTEGER  { none(1), m-m(2), other(3) }
	ACCESS read-only
	STATUS mandatory
	DESCRIPTION
	   "PC_Withhold, (refer to ANSI SMT 9.4.1)."
	::= { fnnMSFBMICPortEntry 9 }

fnnMSFBMICPortLerCondition OBJECT-TYPE
	SYNTAX INTEGER  { bad(1), okay(2) }
	ACCESS read-only
	STATUS mandatory
	DESCRIPTION
	   "This variable is set to true whenever LerEstimate
	    is less than or equal to LerAlarm (the larger the number
	    the smaller the value)."
	::= { fnnMSFBMICPortEntry 10 }


-- Trunk Table
-- (only present for compatibility)

fnnMSFBMICTrunkTable OBJECT-TYPE
	SYNTAX SEQUENCE OF FnnMSFBMICTrunkEntry
	ACCESS not-accessible
	STATUS mandatory
	DESCRIPTION
		"FDDI module specific trunk table variables.
		 At present there are none."
	::= { fnnMSFBMIC 3 }

fnnMSFBMICTrunkEntry OBJECT-TYPE
	SYNTAX FnnMSFBMICTrunkEntry
	ACCESS not-accessible
	STATUS mandatory
	DESCRIPTION
		"A description of fnnMS-FBMIC trunk attributes."
	INDEX { fnnMSFBMICTrunkSlotIndex, fnnMSFBMICTrunkIndex }
	::= { fnnMSFBMICTrunkTable 1 }

FnnMSFBMICTrunkEntry ::=
	SEQUENCE {
		fnnMSFBMICTrunkSlotIndex
			INTEGER,
		fnnMSFBMICTrunkIndex
			INTEGER
		}

fnnMSFBMICTrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { fnnMSFBMICTrunkEntry 1 }


fnnMSFBMICTrunkIndex OBJECT-TYPE
	SYNTAX INTEGER
	ACCESS read-only
	STATUS mandatory
	DESCRIPTION
		"A unique value that identifies a particular trunk within this
		module. Its value ranges between 1 and modTrunkNumber.
		The module identified by a particular value of this index is
		the same module as indentified by the same value of
		trunkIndex."
	::= { fnnMSFBMICTrunkEntry 2 }


--
-- FDDI media module, for fiber with ST connector
--

fnnMSSTModTable OBJECT-TYPE
	SYNTAX SEQUENCE OF FnnMSSTModEntry
	ACCESS not-accessible
	STATUS mandatory
	DESCRIPTION
		"A list of module attributes that apply to this model.
		To access an fnnMSSTModTable entry, the
		fnnMSSTModSlotIndex attribute is used."
	::= { fnnMSST 1 }

fnnMSSTModEntry OBJECT-TYPE
	SYNTAX FnnMSSTModEntry
	ACCESS not-accessible
	STATUS mandatory
	DESCRIPTION
		"A list of module-specific information about a specific
		fnnMS-ST module in the concentrator."
	INDEX { fnnMSSTModSlotIndex }
	::= { fnnMSSTModTable 1 }

FnnMSSTModEntry ::=
	SEQUENCE {
		fnnMSSTModSlotIndex
			INTEGER,
		fnnMSSTModDownStreamModule
			INTEGER,
		fnnMSSTModUpStreamModule
			INTEGER,
		fnnMSSTModDownStreamOperPath
			INTEGER,
		fnnMSSTModUpStreamOperPath
			INTEGER,
		fnnMSSTModRingInfo
			OCTET STRING
		}

fnnMSSTModSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of modSlotIndex."
	::= { fnnMSSTModEntry 1 }

fnnMSSTModDownStreamModule OBJECT-TYPE
	SYNTAX INTEGER (1..16)
	ACCESS read-only
	STATUS mandatory
	DESCRIPTION
		"Down stream slot (transmit to)"
	::= { fnnMSSTModEntry 2 }

fnnMSSTModUpStreamModule OBJECT-TYPE
	SYNTAX INTEGER (1..16)
	ACCESS read-only
	STATUS mandatory
	DESCRIPTION
		"Up stream slot (receive from)"
	::= { fnnMSSTModEntry 3 }

fnnMSSTModDownStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"Transmit DBA (debug only)"
	::= { fnnMSSTModEntry 4 }

fnnMSSTModUpStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"Receive DBA (debug only)"
	::= { fnnMSSTModEntry 5 }

fnnMSSTModRingInfo OBJECT-TYPE
	SYNTAX OCTET STRING (SIZE(1..8))
	ACCESS read-only
	STATUS mandatory
	DESCRIPTION
		"An array which is indexed by DBA number. Each element
		 contains the slot number (1..16) which is assigned to
		 transmit on this DBA. (debug only)"
	::= { fnnMSSTModEntry 6 }


-- port table

fnnMSSTPortTable OBJECT-TYPE
	SYNTAX SEQUENCE OF FnnMSSTPortEntry
	ACCESS not-accessible
	STATUS mandatory
	DESCRIPTION
		"A table of port-specific information for each port of
		this module type."
	::= { fnnMSST 2 }

fnnMSSTPortEntry OBJECT-TYPE
	SYNTAX FnnMSSTPortEntry
	ACCESS not-accessible
	STATUS mandatory
	DESCRIPTION
		"A list of module-specific information about a specific
		fnnMS-ST port in the concentrator."
	INDEX { fnnMSSTPortSlotIndex, fnnMSSTPortIndex }
	::= { fnnMSSTPortTable 1 }

FnnMSSTPortEntry ::=
	SEQUENCE {
		fnnMSSTPortSlotIndex
			INTEGER,
		fnnMSSTPortIndex
			INTEGER,
		fnnMSSTPortConfig
			INTEGER,
		fnnMSSTPortPcmState
			INTEGER,
		fnnMSSTPortConnectState
			INTEGER,
		fnnMSSTPortNeighbor
			INTEGER,
		fnnMSSTPortRemoteMACIndicated
			INTEGER,
		fnnMSSTPortBSFlag
			INTEGER,
		fnnMSSTPortPCWithhold
			INTEGER,
		fnnMSSTPortLerCondition
			INTEGER
		}

fnnMSSTPortSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		portSlotIndex."
	::= { fnnMSSTPortEntry 1 }


fnnMSSTPortIndex OBJECT-TYPE
	SYNTAX INTEGER
	ACCESS read-only
	STATUS mandatory
	DESCRIPTION
		"A unique value that identifies a particular port within this
		module. Its value ranges between 1 and modPortNumber.
		The module identified by a particular value of this index is
		the same module as indentified by the same value of
		portIndex."
	::= { fnnMSSTPortEntry 2 }

fnnMSSTPortConfig OBJECT-TYPE
	SYNTAX INTEGER {
		slave(3),
		master(4)
		}
	ACCESS read-write
	STATUS mandatory
	DESCRIPTION
		"Specifies the FDDI port type. If the port is on an
		 FFM, the only allowed values are slave(3) and master(4).
		 In addition, there can only be one active slave port on any
		 concentrator FDDI network."
	::= { fnnMSSTPortEntry 3 }

fnnMSSTPortPcmState OBJECT-TYPE
	SYNTAX INTEGER {
		  pc0(1), -- Off
		  pc1(2), -- Break
		  pc2(3), -- Trace
		  pc3(4), -- Connect
		  pc4(5), -- Next
		  pc5(6), -- Signal
		  pc6(7), -- Join
		  pc7(8), -- Verify
		  pc8(9), -- Active
		  pc9(10) -- Maint
	}
	ACCESS read-only
	STATUS mandatory
	DESCRIPTION
		      "(refer to ANSI SMT 9.6.2)."
	::= { fnnMSSTPortEntry 4 }

fnnMSSTPortConnectState OBJECT-TYPE
	SYNTAX INTEGER {
	  disabled(1),
	  connecting(2),
	  standby(3),
	  active(4)
		}
	ACCESS read-only
	STATUS mandatory
	DESCRIPTION
	     "An indication of the connect state of this PORT.
	      Basically, this gives a higher level view of the
	      state of the connection by grouping PCM states and
	      the PC-Withhold flag state.  The supported values
	      and their corresponding PCM states and PC-Withhold
	      condition, when relevant, are:
		  disabled: (PC0:Off, PC9:Maint)
		  connecting: (PC1(Break) || PC3 (Connect) || PC4(next) ||
			       PC5 (Signal) || PC6(Join) || PC7 (Verify)) &&
			      (PC_Withhold = None)
		  standby: (PC_Withhold != None)
		  active: (PC2:Trace || PC8:Active)"
	::= { fnnMSSTPortEntry 5 }

fnnMSSTPortNeighbor OBJECT-TYPE
	SYNTAX INTEGER {
		a(1),
		b(2),
		slave(3),
		master(4),
		unknown(5)
		}
	ACCESS read-only
	STATUS mandatory
	DESCRIPTION
	     "The type (PC_Neighbor) of the remote PORT that is
	      determined in PC_Signaling in R_Val (1,2) (refer
	      to ANSI SMT 9.6.3.2)."
	::= { fnnMSSTPortEntry 6 }

fnnMSSTPortRemoteMACIndicated OBJECT-TYPE
	SYNTAX INTEGER { true(1), false(2) }
	ACCESS read-only
	STATUS mandatory
	DESCRIPTION
	  "The indication, in PC-Signaling that the remote
	   partner intends to place a MAC in the output token
	   PATH of this PORT.  Signaled as R_Val (9) (refer
	   to ANSI SMT 9.6.3.2)."
	::= { fnnMSSTPortEntry 7 }

fnnMSSTPortBSFlag OBJECT-TYPE
	SYNTAX INTEGER { true(1), false(2) }
	ACCESS read-only
	STATUS mandatory
	DESCRIPTION
	  "The Break State, BS_Flag (refer to ANSI SMT
	   9.4.3.4)."
	::= { fnnMSSTPortEntry 8 }

fnnMSSTPortPCWithhold OBJECT-TYPE
	SYNTAX INTEGER  { none(1), m-m(2), other(3) }
	ACCESS read-only
	STATUS mandatory
	DESCRIPTION
	   "PC_Withhold, (refer to ANSI SMT 9.4.1)."
	::= { fnnMSSTPortEntry 9 }

fnnMSSTPortLerCondition OBJECT-TYPE
	SYNTAX INTEGER  { bad(1), okay(2) }
	ACCESS read-only
	STATUS mandatory
	DESCRIPTION
	   "This variable is set to true whenever LerEstimate
	    is less than or equal to LerAlarm (the larger the number
	    the smaller the value)."
	::= { fnnMSSTPortEntry 10 }


-- Trunk Table
-- (only present for compatibility)

fnnMSSTTrunkTable OBJECT-TYPE
	SYNTAX SEQUENCE OF FnnMSSTTrunkEntry
	ACCESS not-accessible
	STATUS mandatory
	DESCRIPTION
		"FDDI module specific trunk table variables.
		 At present there are none."
	::= { fnnMSST 3 }

fnnMSSTTrunkEntry OBJECT-TYPE
	SYNTAX FnnMSSTTrunkEntry
	ACCESS not-accessible
	STATUS mandatory
	DESCRIPTION
		"A description of fnnMS-ST trunk attributes."
	INDEX { fnnMSSTTrunkSlotIndex, fnnMSSTTrunkIndex }
	::= { fnnMSSTTrunkTable 1 }

FnnMSSTTrunkEntry ::=
	SEQUENCE {
		fnnMSSTTrunkSlotIndex
			INTEGER,
		fnnMSSTTrunkIndex
			INTEGER
		}

fnnMSSTTrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { fnnMSSTTrunkEntry 1 }


fnnMSSTTrunkIndex OBJECT-TYPE
	SYNTAX INTEGER
	ACCESS read-only
	STATUS mandatory
	DESCRIPTION
		"A unique value that identifies a particular trunk within this
		module. Its value ranges between 1 and modTrunkNumber.
		The module identified by a particular value of this index is
		the same module as indentified by the same value of
		trunkIndex."
	::= { fnnMSSTTrunkEntry 2 }


--
-- FDDI media module, for shielded copper with DB9 connector.
--

fnnMSDB9ModTable OBJECT-TYPE
	SYNTAX SEQUENCE OF FnnMSDB9ModEntry
	ACCESS not-accessible
	STATUS mandatory
	DESCRIPTION
		"A list of module attributes that apply to this model.
		To access an fnnMSDB9ModTable entry, the
		fnnMSDB9ModSlotIndex attribute is used."
	::= { fnnMSDB9 1 }

fnnMSDB9ModEntry OBJECT-TYPE
	SYNTAX FnnMSDB9ModEntry
	ACCESS not-accessible
	STATUS mandatory
	DESCRIPTION
		"A list of module-specific information about a specific
		fnnMS-DB9 module in the concentrator."
	INDEX { fnnMSDB9ModSlotIndex }
	::= { fnnMSDB9ModTable 1 }

FnnMSDB9ModEntry ::=
	SEQUENCE {
		fnnMSDB9ModSlotIndex
			INTEGER,
		fnnMSDB9ModDownStreamModule
			INTEGER,
		fnnMSDB9ModUpStreamModule
			INTEGER,
		fnnMSDB9ModDownStreamOperPath
			INTEGER,
		fnnMSDB9ModUpStreamOperPath
			INTEGER,
		fnnMSDB9ModRingInfo
			OCTET STRING
		}

fnnMSDB9ModSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of modSlotIndex."
	::= { fnnMSDB9ModEntry 1 }

fnnMSDB9ModDownStreamModule OBJECT-TYPE
	SYNTAX INTEGER (1..16)
	ACCESS read-only
	STATUS mandatory
	DESCRIPTION
		"Down stream slot (transmit to)"
	::= { fnnMSDB9ModEntry 2 }

fnnMSDB9ModUpStreamModule OBJECT-TYPE
	SYNTAX INTEGER (1..16)
	ACCESS read-only
	STATUS mandatory
	DESCRIPTION
		"Down stream slot (receive from)"
	::= { fnnMSDB9ModEntry 3 }

fnnMSDB9ModDownStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"transmit DBA  (debug only)"
	::= { fnnMSDB9ModEntry 4 }

fnnMSDB9ModUpStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"receive DBA  (debug only)"
	::= { fnnMSDB9ModEntry 5 }

fnnMSDB9ModRingInfo OBJECT-TYPE
	SYNTAX OCTET STRING (SIZE(1..8))
	ACCESS read-only
	STATUS mandatory
	DESCRIPTION
		"An array which is indexed by DBA number. Each element
		 contains the slot number (1..16) which is assigned to
		 transmit on this DBA. (debug only)"
	::= { fnnMSDB9ModEntry 6 }


-- port table

fnnMSDB9PortTable OBJECT-TYPE
	SYNTAX SEQUENCE OF FnnMSDB9PortEntry
	ACCESS not-accessible
	STATUS mandatory
	DESCRIPTION
		"A table of port-specific information for each port of
		this module type."
	::= { fnnMSDB9 2 }

fnnMSDB9PortEntry OBJECT-TYPE
	SYNTAX FnnMSDB9PortEntry
	ACCESS not-accessible
	STATUS mandatory
	DESCRIPTION
		"A list of module-specific information about a specific
		fnnMS-DB9 port in the concentrator."
	INDEX { fnnMSDB9PortSlotIndex, fnnMSDB9PortIndex }
	::= { fnnMSDB9PortTable 1 }

FnnMSDB9PortEntry ::=
	SEQUENCE {
		fnnMSDB9PortSlotIndex
			INTEGER,
		fnnMSDB9PortIndex
			INTEGER,
		fnnMSDB9PortConfig
			INTEGER,
		fnnMSDB9PortPcmState
			INTEGER,
		fnnMSDB9PortConnectState
			INTEGER,
		fnnMSDB9PortNeighbor
			INTEGER,
		fnnMSDB9PortRemoteMACIndicated
			INTEGER,
		fnnMSDB9PortBSFlag
			INTEGER,
		fnnMSDB9PortPCWithhold
			INTEGER,
		fnnMSDB9PortLerCondition
			INTEGER,
		fnnMSDB9PortPersonality
			INTEGER
		}

fnnMSDB9PortSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		portSlotIndex."
	::= { fnnMSDB9PortEntry 1 }


fnnMSDB9PortIndex OBJECT-TYPE
	SYNTAX INTEGER
	ACCESS read-only
	STATUS mandatory
	DESCRIPTION
		"A unique value that identifies a particular port within this
		module. Its value ranges between 1 and modPortNumber.
		The module identified by a particular value of this index is
		the same module as indentified by the same value of
		portIndex."
	::= { fnnMSDB9PortEntry 2 }

fnnMSDB9PortConfig OBJECT-TYPE
	SYNTAX INTEGER {
		slave(3),
		master(4)
		}
	ACCESS read-write
	STATUS mandatory
	DESCRIPTION
		"Specifies the FDDI port type. If the port is on an
		 FFM, the only allowed values are slave(3) and master(4).
		 In addition, there can only be one active slave port on any
		 concentrator FDDI network."
	::= { fnnMSDB9PortEntry 3 }

fnnMSDB9PortPcmState OBJECT-TYPE
	SYNTAX INTEGER {
		  pc0(1), -- Off
		  pc1(2), -- Break
		  pc2(3), -- Trace
		  pc3(4), -- Connect
		  pc4(5), -- Next
		  pc5(6), -- Signal
		  pc6(7), -- Join
		  pc7(8), -- Verify
		  pc8(9), -- Active
		  pc9(10) -- Maint
	}
	ACCESS read-only
	STATUS mandatory
	DESCRIPTION
		      "(refer to ANSI SMT 9.6.2)."
	::= { fnnMSDB9PortEntry 4 }

fnnMSDB9PortConnectState OBJECT-TYPE
	SYNTAX INTEGER {
	  disabled(1),
	  connecting(2),
	  standby(3),
	  active(4)
		}
	ACCESS read-only
	STATUS mandatory
	DESCRIPTION
	     "An indication of the connect state of this PORT.
	      Basically, this gives a higher level view of the
	      state of the connection by grouping PCM states and
	      the PC-Withhold flag state.  The supported values
	      and their corresponding PCM states and PC-Withhold
	      condition, when relevant, are:
		  disabled: (PC0:Off, PC9:Maint)
		  connecting: (PC1(Break) || PC3 (Connect) || PC4(next) ||
			       PC5 (Signal) || PC6(Join) || PC7 (Verify)) &&
			      (PC_Withhold = None)
		  standby: (PC_Withhold != None)
		  active: (PC2:Trace || PC8:Active)"
	::= { fnnMSDB9PortEntry 5 }

fnnMSDB9PortNeighbor OBJECT-TYPE
	SYNTAX INTEGER {
		a(1),
		b(2),
		slave(3),
		master(4),
		unknown(5)
		}
	ACCESS read-only
	STATUS mandatory
	DESCRIPTION
	     "The type (PC_Neighbor) of the remote PORT that is
	      determined in PC_Signaling in R_Val (1,2) (refer
	      to ANSI SMT 9.6.3.2)."
	::= { fnnMSDB9PortEntry 6 }

fnnMSDB9PortRemoteMACIndicated OBJECT-TYPE
	SYNTAX INTEGER { true(1), false(2) }
	ACCESS read-only
	STATUS mandatory
	DESCRIPTION
	  "The indication, in PC-Signaling that the remote
	   partner intends to place a MAC in the output token
	   PATH of this PORT.  Signaled as R_Val (9) (refer
	   to ANSI SMT 9.6.3.2)."
	::= { fnnMSDB9PortEntry 7 }

fnnMSDB9PortBSFlag OBJECT-TYPE
	SYNTAX INTEGER { true(1), false(2) }
	ACCESS read-only
	STATUS mandatory
	DESCRIPTION
	  "The Break State, BS_Flag (refer to ANSI SMT
	   9.4.3.4)."
	::= { fnnMSDB9PortEntry 8 }

fnnMSDB9PortPCWithhold OBJECT-TYPE
	SYNTAX INTEGER  { none(1), m-m(2), other(3) }
	ACCESS read-only
	STATUS mandatory
	DESCRIPTION
	   "PC_Withhold, (refer to ANSI SMT 9.4.1)."
	::= { fnnMSDB9PortEntry 9 }

fnnMSDB9PortLerCondition OBJECT-TYPE
	SYNTAX INTEGER  { bad(1), okay(2) }
	ACCESS read-only
	STATUS mandatory
	DESCRIPTION
	   "This variable is set to true whenever LerEstimate
	    is less than or equal to LerAlarm (the larger the number
	    the smaller the value)."
	::= { fnnMSDB9PortEntry 10 }


fnnMSDB9PortPersonality OBJECT-TYPE
	SYNTAX INTEGER {
		sddi(1),
		tpddi(2)
		}
	ACCESS read-write
	STATUS mandatory
	DESCRIPTION
		"Specifies the physical signaling used by the port, the only
		 valid values are sddi(3) and tpddi(4)."
	::= { fnnMSDB9PortEntry 11 }


-- Trunk Table
-- (only present for compatibility)

fnnMSDB9TrunkTable OBJECT-TYPE
	SYNTAX SEQUENCE OF FnnMSDB9TrunkEntry
	ACCESS not-accessible
	STATUS mandatory
	DESCRIPTION
		"FDDI module specific trunk table variables.
		 At present there are none."
	::= { fnnMSDB9 3 }

fnnMSDB9TrunkEntry OBJECT-TYPE
	SYNTAX FnnMSDB9TrunkEntry
	ACCESS not-accessible
	STATUS mandatory
	DESCRIPTION
		"A description of fnnMS-DB9 trunk attributes."
	INDEX { fnnMSDB9TrunkSlotIndex, fnnMSDB9TrunkIndex }
	::= { fnnMSDB9TrunkTable 1 }

FnnMSDB9TrunkEntry ::=
	SEQUENCE {
		fnnMSDB9TrunkSlotIndex
			INTEGER,
		fnnMSDB9TrunkIndex
			INTEGER
		}

fnnMSDB9TrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { fnnMSDB9TrunkEntry 1 }


fnnMSDB9TrunkIndex OBJECT-TYPE
	SYNTAX INTEGER
	ACCESS read-only
	STATUS mandatory
	DESCRIPTION
		"A unique value that identifies a particular trunk within this
		module. Its value ranges between 1 and modTrunkNumber.
		The module identified by a particular value of this index is
		the same module as indentified by the same value of
		trunkIndex."
	::= { fnnMSDB9TrunkEntry 2 }


--
-- FDDI media module, for copper with RJ45 connector.
--

tnnMSTDDIModTable OBJECT-TYPE
	SYNTAX SEQUENCE OF TnnMSTDDIModEntry
	ACCESS not-accessible
	STATUS mandatory
	DESCRIPTION
		"A list of module attributes that apply to this model.
		To access an tnnMSTDDIModTable entry, the
		tnnMSTDDIModSlotIndex attribute is used."
	::= { tnnMSTDDI 1 }

tnnMSTDDIModEntry OBJECT-TYPE
	SYNTAX TnnMSTDDIModEntry
	ACCESS not-accessible
	STATUS mandatory
	DESCRIPTION
		"A list of module-specific information about a specific
		tnnMS-TDDI module in the concentrator."
	INDEX { tnnMSTDDIModSlotIndex }
	::= { tnnMSTDDIModTable 1 }

TnnMSTDDIModEntry ::=
	SEQUENCE {
		tnnMSTDDIModSlotIndex
			INTEGER,
		tnnMSTDDIModDownStreamModule
			INTEGER,
		tnnMSTDDIModUpStreamModule
			INTEGER,
		tnnMSTDDIModDownStreamOperPath
			INTEGER,
		tnnMSTDDIModUpStreamOperPath
			INTEGER,
		tnnMSTDDIModRingInfo
			OCTET STRING
		}

tnnMSTDDIModSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of modSlotIndex."
	::= { tnnMSTDDIModEntry 1 }

tnnMSTDDIModDownStreamModule OBJECT-TYPE
	SYNTAX INTEGER (1..16)
	ACCESS read-only
	STATUS mandatory
	DESCRIPTION
		"Down stream slot (transmit to)"
	::= { tnnMSTDDIModEntry 2 }

tnnMSTDDIModUpStreamModule OBJECT-TYPE
	SYNTAX INTEGER (1..16)
	ACCESS read-only
	STATUS mandatory
	DESCRIPTION
		"Down stream slot (receive from)"
	::= { tnnMSTDDIModEntry 3 }

tnnMSTDDIModDownStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"transmit DBA  (debug only)"
	::= { tnnMSTDDIModEntry 4 }

tnnMSTDDIModUpStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"receive DBA  (debug only)"
	::= { tnnMSTDDIModEntry 5 }

tnnMSTDDIModRingInfo OBJECT-TYPE
	SYNTAX OCTET STRING (SIZE(1..8))
	ACCESS read-only
	STATUS mandatory
	DESCRIPTION
		"An array which is indexed by DBA number. Each element
		 contains the slot number (1..16) which is assigned to
		 transmit on this DBA. (debug only)"
	::= { tnnMSTDDIModEntry 6 }


-- port table

tnnMSTDDIPortTable OBJECT-TYPE
	SYNTAX SEQUENCE OF TnnMSTDDIPortEntry
	ACCESS not-accessible
	STATUS mandatory
	DESCRIPTION
		"A table of port-specific information for each port of
		this module type."
	::= { tnnMSTDDI 2 }

tnnMSTDDIPortEntry OBJECT-TYPE
	SYNTAX TnnMSTDDIPortEntry
	ACCESS not-accessible
	STATUS mandatory
	DESCRIPTION
		"A list of module-specific information about a specific
		tnnMS-TDDI port in the concentrator."
	INDEX { tnnMSTDDIPortSlotIndex, tnnMSTDDIPortIndex }
	::= { tnnMSTDDIPortTable 1 }

TnnMSTDDIPortEntry ::=
	SEQUENCE {
		tnnMSTDDIPortSlotIndex
			INTEGER,
		tnnMSTDDIPortIndex
			INTEGER,
		tnnMSTDDIPortConfig
			INTEGER,
		tnnMSTDDIPortPcmState
			INTEGER,
		tnnMSTDDIPortConnectState
			INTEGER,
		tnnMSTDDIPortNeighbor
			INTEGER,
		tnnMSTDDIPortRemoteMACIndicated
			INTEGER,
		tnnMSTDDIPortBSFlag
			INTEGER,
		tnnMSTDDIPortPCWithhold
			INTEGER,
		tnnMSTDDIPortLerCondition
			INTEGER
		}

tnnMSTDDIPortSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		portSlotIndex."
	::= { tnnMSTDDIPortEntry 1 }


tnnMSTDDIPortIndex OBJECT-TYPE
	SYNTAX INTEGER
	ACCESS read-only
	STATUS mandatory
	DESCRIPTION
		"A unique value that identifies a particular port within this
		module. Its value ranges between 1 and modPortNumber.
		The module identified by a particular value of this index is
		the same module as indentified by the same value of
		portIndex."
	::= { tnnMSTDDIPortEntry 2 }

tnnMSTDDIPortConfig OBJECT-TYPE
	SYNTAX INTEGER {
		slave(3),
		master(4)
		}
	ACCESS read-write
	STATUS mandatory
	DESCRIPTION
		"Specifies the FDDI port type. If the port is on an
		 FFM, the only allowed values are slave(3) and master(4).
		 In addition, there can only be one active slave port on any
		 concentrator FDDI network."
	::= { tnnMSTDDIPortEntry 3 }

tnnMSTDDIPortPcmState OBJECT-TYPE
	SYNTAX INTEGER {
		  pc0(1), -- Off
		  pc1(2), -- Break
		  pc2(3), -- Trace
		  pc3(4), -- Connect
		  pc4(5), -- Next
		  pc5(6), -- Signal
		  pc6(7), -- Join
		  pc7(8), -- Verify
		  pc8(9), -- Active
		  pc9(10) -- Maint
	}
	ACCESS read-only
	STATUS mandatory
	DESCRIPTION
		      "(refer to ANSI SMT 9.6.2)."
	::= { tnnMSTDDIPortEntry 4 }

tnnMSTDDIPortConnectState OBJECT-TYPE
	SYNTAX INTEGER {
	  disabled(1),
	  connecting(2),
	  standby(3),
	  active(4)
		}
	ACCESS read-only
	STATUS mandatory
	DESCRIPTION
	     "An indication of the connect state of this PORT.
	      Basically, this gives a higher level view of the
	      state of the connection by grouping PCM states and
	      the PC-Withhold flag state.  The supported values
	      and their corresponding PCM states and PC-Withhold
	      condition, when relevant, are:
		  disabled: (PC0:Off, PC9:Maint)
		  connecting: (PC1(Break) || PC3 (Connect) || PC4(next) ||
			       PC5 (Signal) || PC6(Join) || PC7 (Verify)) &&
			      (PC_Withhold = None)
		  standby: (PC_Withhold != None)
		  active: (PC2:Trace || PC8:Active)"
	::= { tnnMSTDDIPortEntry 5 }

tnnMSTDDIPortNeighbor OBJECT-TYPE
	SYNTAX INTEGER {
		a(1),
		b(2),
		slave(3),
		master(4),
		unknown(5)
		}
	ACCESS read-only
	STATUS mandatory
	DESCRIPTION
	     "The type (PC_Neighbor) of the remote PORT that is
	      determined in PC_Signaling in R_Val (1,2) (refer
	      to ANSI SMT 9.6.3.2)."
	::= { tnnMSTDDIPortEntry 6 }

tnnMSTDDIPortRemoteMACIndicated OBJECT-TYPE
	SYNTAX INTEGER { true(1), false(2) }
	ACCESS read-only
	STATUS mandatory
	DESCRIPTION
	  "The indication, in PC-Signaling that the remote
	   partner intends to place a MAC in the output token
	   PATH of this PORT.  Signaled as R_Val (9) (refer
	   to ANSI SMT 9.6.3.2)."
	::= { tnnMSTDDIPortEntry 7 }

tnnMSTDDIPortBSFlag OBJECT-TYPE
	SYNTAX INTEGER { true(1), false(2) }
	ACCESS read-only
	STATUS mandatory
	DESCRIPTION
	  "The Break State, BS_Flag (refer to ANSI SMT
	   9.4.3.4)."
	::= { tnnMSTDDIPortEntry 8 }

tnnMSTDDIPortPCWithhold OBJECT-TYPE
	SYNTAX INTEGER  { none(1), m-m(2), other(3) }
	ACCESS read-only
	STATUS mandatory
	DESCRIPTION
	   "PC_Withhold, (refer to ANSI SMT 9.4.1)."
	::= { tnnMSTDDIPortEntry 9 }

tnnMSTDDIPortLerCondition OBJECT-TYPE
	SYNTAX INTEGER  { bad(1), okay(2) }
	ACCESS read-only
	STATUS mandatory
	DESCRIPTION
	   "This variable is set to true whenever LerEstimate
	    is less than or equal to LerAlarm (the larger the number
	    the smaller the value)."
	::= { tnnMSTDDIPortEntry 10 }

-- Trunk Table
-- (only present for compatibility)

tnnMSTDDITrunkTable OBJECT-TYPE
	SYNTAX SEQUENCE OF TnnMSTDDITrunkEntry
	ACCESS not-accessible
	STATUS mandatory
	DESCRIPTION
		"FDDI module specific trunk table variables.
		 At present there are none."
	::= { tnnMSTDDI 3 }

tnnMSTDDITrunkEntry OBJECT-TYPE
	SYNTAX TnnMSTDDITrunkEntry
	ACCESS not-accessible
	STATUS mandatory
	DESCRIPTION
		"A description of tnnMS-TDDI trunk attributes."
	INDEX { tnnMSTDDITrunkSlotIndex, tnnMSTDDITrunkIndex }
	::= { tnnMSTDDITrunkTable 1 }

TnnMSTDDITrunkEntry ::=
	SEQUENCE {
		tnnMSTDDITrunkSlotIndex
			INTEGER,
		tnnMSTDDITrunkIndex
			INTEGER
		}

tnnMSTDDITrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { tnnMSTDDITrunkEntry 1 }


tnnMSTDDITrunkIndex OBJECT-TYPE
	SYNTAX INTEGER
	ACCESS read-only
	STATUS mandatory
	DESCRIPTION
		"A unique value that identifies a particular trunk within this
		module. Its value ranges between 1 and modTrunkNumber.
		The module identified by a particular value of this index is
		the same module as indentified by the same value of
		trunkIndex."
	::= { tnnMSTDDITrunkEntry 2 }


--
-- Ethernet 10BASE-T Per-Connector Module
--

ennCSTELCOModTable OBJECT-TYPE
	SYNTAX SEQUENCE OF EnnCSTELCOModEntry
	ACCESS not-accessible
	STATUS mandatory
	DESCRIPTION
		"A list of module-specific information about a specific
		ennCS-TELCO module in the concentrator."
	::= { ennCSTELCO 1 }

ennCSTELCOModEntry OBJECT-TYPE
	SYNTAX EnnCSTELCOModEntry
	ACCESS not-accessible
	STATUS mandatory
	DESCRIPTION
		"A list of module-specific information about a specific
		ennCS-TELCO module in the concentrator."
	INDEX { ennCSTELCOModSlotIndex }
	::= { ennCSTELCOModTable 1 }

EnnCSTELCOModEntry ::=
	SEQUENCE {
		ennCSTELCOModSlotIndex
			INTEGER,
		ennCSTELCOModMonitorConn
			INTEGER,
		ennCSTELCOModConn1Network
			INTEGER,
		ennCSTELCOModConn2Network
			INTEGER,
		ennCSTELCOModConn1DipNetwork
			INTEGER,
		ennCSTELCOModConn2DipNetwork
			INTEGER,
		ennCSTELCOModAutoPartition
			INTEGER
		}

ennCSTELCOModSlotIndex OBJECT-TYPE
	SYNTAX INTEGER
	ACCESS read-only
	STATUS mandatory
	DESCRIPTION
		"The slot number of this module."
	::= { ennCSTELCOModEntry 1 }

ennCSTELCOModMonitorConn OBJECT-TYPE
	SYNTAX INTEGER {
		connector-1(1),
		connector-2(2)
		}
	ACCESS read-write
	STATUS mandatory
	DESCRIPTION
		"When both connectors are on the same network:

		   Setting this object to connector-1 allows the EMM to
		   monitor the port statistics of port 1-12 on a per-port
		   basis, and the port statistics of port 13-24 are summed
		   and are reported through port 13.

		   Setting this object to connector-2 allows the EMM to
		   monitor the port statistics of port 12-24 on a per-port
		   basis, and the port statistics of port 1-12 are summed
		   and are reported through port 13.

		 Note: when the 2 connectors are on different networks,
		 setting this object to the value connector-1 or
		 connector-2 will not have any effect.  The port counters
		 will be cleared whenever the value of this object is
		 changed."
	::= { ennCSTELCOModEntry 2 }

ennCSTELCOModConn1Network OBJECT-TYPE
	SYNTAX INTEGER {
		ethernet-1(6),
		ethernet-2(7),
		ethernet-3(8),
		isolated-1(21),
		isolated-2(22)
		}
	ACCESS read-write
	STATUS mandatory
	DESCRIPTION
		"The network that this connector is attached to."
	::= { ennCSTELCOModEntry 3 }

ennCSTELCOModConn2Network OBJECT-TYPE
	SYNTAX INTEGER {
		ethernet-1(6),
		ethernet-2(7),
		ethernet-3(8),
		isolated-1(21),
		isolated-2(22)
		}
	ACCESS read-write
	STATUS mandatory
	DESCRIPTION
		"The network that this connector is attached to."

	::= { ennCSTELCOModEntry 4 }

ennCSTELCOModConn1DipNetwork OBJECT-TYPE
	SYNTAX INTEGER {
		ethernet-1(6),
		ethernet-2(7),
		ethernet-3(8),
		isolated-1(21),
		isolated-2(22)
		}
	ACCESS read-only
	STATUS mandatory
	DESCRIPTION
		"The network indicated by the connector dip switch."
	::= { ennCSTELCOModEntry 5 }

ennCSTELCOModConn2DipNetwork OBJECT-TYPE
	SYNTAX INTEGER {
		ethernet-1(6),
		ethernet-2(7),
		ethernet-3(8),
		isolated-1(21),
		isolated-2(22)
		}
	ACCESS read-only
	STATUS mandatory
	DESCRIPTION
		"The network indicated by the connector dip switch."
	::= { ennCSTELCOModEntry 6 }

ennCSTELCOModAutoPartition OBJECT-TYPE
	SYNTAX INTEGER {
		collisions-31(1),
		collisions-63(2),
		collisions-127(3),
		collisions-255(4)
		}
	ACCESS read-write
	STATUS mandatory
	DESCRIPTION
		"This object holds the consecutive collision count
		 limit value.  The module goes into the auto-partition
		 mode whenever the consecutive collision count exceeds
		 the consecutive collision limit count."
	::= { ennCSTELCOModEntry 7 }

ennCSTELCOPortTable OBJECT-TYPE
	SYNTAX SEQUENCE OF EnnCSTELCOPortEntry
	ACCESS not-accessible
	STATUS mandatory
	DESCRIPTION
		"A table of port-specific information for each port of
		this module type."
	::= { ennCSTELCO 2 }

ennCSTELCOPortEntry OBJECT-TYPE
	SYNTAX EnnCSTELCOPortEntry
	ACCESS not-accessible
	STATUS mandatory
	DESCRIPTION
		"A list of module-specific information about a specific
		ennCS-TELCO port in the concentrator."
	INDEX { ennCSTELCOPortSlotIndex, ennCSTELCOPortIndex }
	::= { ennCSTELCOPortTable 1 }

EnnCSTELCOPortEntry ::=
	SEQUENCE {
		ennCSTELCOPortSlotIndex
			INTEGER,
		ennCSTELCOPortIndex
			INTEGER,
		ennCSTELCOPortAdminState
			INTEGER,
		ennCSTELCOPortBuddySlot
			INTEGER,
		ennCSTELCOPortBuddyPort
			INTEGER,
		ennCSTELCOPortDipAdminState
			INTEGER,
		ennCSTELCOPortLinkInteg
			INTEGER,
		ennCSTELCOPortDipLinkInteg
			INTEGER
		}

ennCSTELCOPortSlotIndex OBJECT-TYPE
	SYNTAX INTEGER
	ACCESS read-only
	STATUS mandatory
	DESCRIPTION
		"The slot number of this port's module."
	::= { ennCSTELCOPortEntry 1 }


ennCSTELCOPortIndex OBJECT-TYPE
	SYNTAX INTEGER
	ACCESS read-only
	STATUS mandatory
	DESCRIPTION
		"The port number of this port."
	::= { ennCSTELCOPortEntry 2 }

ennCSTELCOPortAdminState OBJECT-TYPE
	SYNTAX INTEGER {
		enabled(1),
		disabled(2),
		redundant-primary(3),
		redundant-backup(4),
		remote-diagnostics(8)
		}
	ACCESS read-write
	STATUS mandatory
	DESCRIPTION
		"The desired state of this port.  Setting this port to
		be redundant or for remote diagnostics with invalid settings
		of buddy slot and buddy port will return the genError error."
	::= { ennCSTELCOPortEntry 3 }

ennCSTELCOPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port.

		If the port is configured for remote diagnostics, then
		this contains the slot index of the backup buddy port.
		To configure a port for remote diagnostics, the buddy's
		slot and port must be set to valid values."
	::= { ennCSTELCOPortEntry 4 }

ennCSTELCOPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port.

		If the port is configured for remote diagnostics, then
		this contains the port index of the backup buddy port.
		To configure a port for remote diagnostics, the buddy's
		slot and port must be set to valid values."
	::= { ennCSTELCOPortEntry 5 }

ennCSTELCOPortDipAdminState OBJECT-TYPE
	SYNTAX INTEGER {
		enabled(1),
		disabled(2)
		}
	ACCESS read-only
	STATUS mandatory
	DESCRIPTION
		"The state of this port as indicated by the port's dip
		switches."
	::= { ennCSTELCOPortEntry 6 }

ennCSTELCOPortLinkInteg OBJECT-TYPE
	SYNTAX INTEGER {
		enabled(1),
		disabled(2)
		}
	ACCESS read-write
	STATUS mandatory
	DESCRIPTION
		"The current link integrity configuration for this port."
	::= { ennCSTELCOPortEntry 7 }

ennCSTELCOPortDipLinkInteg OBJECT-TYPE
	SYNTAX INTEGER {
		enabled(1),
		disabled(2)
		}
	ACCESS read-only
	STATUS mandatory
	DESCRIPTION
		"The link integrity configuration as indicated by this
		dip switch."
	::= { ennCSTELCOPortEntry 8 }


--
-- Token Ring to Token Ring Bridge Module
--

tnnPSBRGModTable OBJECT-TYPE
	SYNTAX SEQUENCE OF TnnPSBRGModEntry
	ACCESS not-accessible
	STATUS mandatory
	DESCRIPTION
		"A table of module-specific information for each
		tnnPS-BRG module in the concentrator."
	::= { tnnPSBRG 1 }

tnnPSBRGModEntry OBJECT-TYPE
	SYNTAX TnnPSBRGModEntry
	ACCESS not-accessible
	STATUS mandatory
	DESCRIPTION
		"A list of module-specific information about a specific
		tnnPS-BRG module in the concentrator."
	INDEX { tnnPSBRGModSlotIndex }
	::= {tnnPSBRGModTable 1 }

TnnPSBRGModEntry ::=
	SEQUENCE {
		tnnPSBRGModSlotIndex
			INTEGER,
		tnnPSBRGModBridgeType
			INTEGER,
		tnnPSBRGModSoftwareVersion
			DisplayString,
		tnnPSBRGModSRBridgeNo
			INTEGER,
		tnnPSBRGModNetworkStatus
			INTEGER
	}

tnnPSBRGModSlotIndex OBJECT-TYPE
	SYNTAX INTEGER
	ACCESS read-only
	STATUS mandatory
	DESCRIPTION
		"The slot number of this module."
	::= { tnnPSBRGModEntry 1 }

tnnPSBRGModBridgeType OBJECT-TYPE
	SYNTAX INTEGER {
		  bridge-type-sr(1),
		  bridge-type-srt(2)
		}
	ACCESS read-only
	STATUS mandatory
	DESCRIPTION
		"Whether the bridge is a source-routing bridge or a
		source-routing-transparent bridge."
	::= { tnnPSBRGModEntry 2 }

tnnPSBRGModSoftwareVersion OBJECT-TYPE
       SYNTAX DisplayString (SIZE(1..10))
       ACCESS read-only
       STATUS mandatory
       DESCRIPTION
	       "The version number of the software loaded into the
		module's flash chips."
       ::= { tnnPSBRGModEntry 3 }

tnnPSBRGModSRBridgeNo OBJECT-TYPE
	SYNTAX INTEGER
	ACCESS read-only
	STATUS mandatory
	DESCRIPTION
		"The module's source routing bridge number."
	::= { tnnPSBRGModEntry 4 }

tnnPSBRGModNetworkStatus OBJECT-TYPE
	SYNTAX INTEGER {
		okay(1),
		closed(2),
		beaconing(3)
		}
	ACCESS read-only
	STATUS mandatory
	DESCRIPTION
		"The status of the ring containing this module."
	::= {tnnPSBRGModEntry 5}

tnnPSBRGPortTable OBJECT-TYPE
	SYNTAX SEQUENCE OF TnnPSBRGPortEntry
	ACCESS not-accessible
	STATUS mandatory
	DESCRIPTION
		"A table of port-specific for each port of each
		tnnPS-BRG module i the concentrator."
	::= { tnnPSBRG 2 }

tnnPSBRGPortEntry OBJECT-TYPE
	SYNTAX TnnPSBRGPortEntry
	ACCESS not-accessible
	STATUS mandatory
	DESCRIPTION
		"A list of port-specific information about a specific
		tnnPS-BRG port in the concentrator."
	INDEX { tnnPSBRGPortSlotIndex, tnnPSBRGPortIndex }
	::= { tnnPSBRGPortTable 1 }

TnnPSBRGPortEntry ::=
	SEQUENCE {
		tnnPSBRGPortSlotIndex
			INTEGER,
		tnnPSBRGPortIndex
			INTEGER,
		tnnPSBRGPortConnector
			INTEGER,
		tnnPSBRGPortSTAPState
			INTEGER,
		tnnPSBRGPortIpAddress
			IpAddress,
		tnnPSBRGPortMACAddress
			OCTET STRING,
		tnnPSBRGPortThroughput
			Gauge,
		tnnPSBRGPortForwarding
			Gauge,
		tnnPSBRGPortSRRingNo
			INTEGER,
		tnnPSBRGPortRingSpeed
			INTEGER
		}

tnnPSBRGPortSlotIndex OBJECT-TYPE
	SYNTAX INTEGER
	ACCESS read-only
	STATUS mandatory
	DESCRIPTION
		"The slot number for this port's module."
	::= { tnnPSBRGPortEntry 1 }

tnnPSBRGPortIndex OBJECT-TYPE
	SYNTAX INTEGER
	ACCESS read-only
	STATUS mandatory
	DESCRIPTION
		"The port number for this port within this slot."
	::= { tnnPSBRGPortEntry 2 }

tnnPSBRGPortConnector OBJECT-TYPE
	SYNTAX INTEGER {
		backPlane(1),	-- connects directly to backplane
		rj45(8),	-- unshielded
		db-9(10)	-- shielded
		}
	ACCESS read-write
	STATUS mandatory
	DESCRIPTION
		"The port connector. Notice that setting port connector
		 available only for the front pannel port."
	::= { tnnPSBRGPortEntry 3 }

tnnPSBRGPortSTAPState OBJECT-TYPE
	SYNTAX INTEGER {
		disabled (1),	-- receive and process frames
		blocking (2),	-- receive and process frames
		listening (3),  -- receive and process frames
		learning (4),	-- receive and process frames
		forwarding (5), -- receive, process and forward frames
		off (6)		-- receive and discard frames
		}
	ACCESS read-only
	STATUS mandatory
	DESCRIPTION
		"The port connector. Notice that setting port connector
		 available only for the front pannel port."
	::= { tnnPSBRGPortEntry 4 }


tnnPSBRGPortIpAddress OBJECT-TYPE
	SYNTAX IpAddress
	ACCESS read-only
	STATUS mandatory
	DESCRIPTION
		"The IP address associated with this port."
	::= { tnnPSBRGPortEntry 5 }

tnnPSBRGPortMACAddress OBJECT-TYPE
	SYNTAX OCTET STRING (SIZE(6))
	ACCESS read-only
	STATUS mandatory
	DESCRIPTION
		"A 6 octet address that uniquely identifies this port."
	::= { tnnPSBRGPortEntry 6 }

tnnPSBRGPortThroughput OBJECT-TYPE
	SYNTAX Gauge
	ACCESS read-only
	STATUS mandatory
	DESCRIPTION
		"Port throughput measured in Kbytes per second."
	::= { tnnPSBRGPortEntry 7 }

tnnPSBRGPortForwarding OBJECT-TYPE
	SYNTAX Gauge
	ACCESS read-only
	STATUS mandatory
	DESCRIPTION
		"Port forwarding rate measured in frames per second."
	::= { tnnPSBRGPortEntry 8 }

tnnPSBRGPortSRRingNo OBJECT-TYPE
	SYNTAX INTEGER
	ACCESS read-only
	STATUS mandatory
	DESCRIPTION
		"The port's source routing ring number."
	::= { tnnPSBRGPortEntry 9 }

tnnPSBRGPortRingSpeed OBJECT-TYPE
	SYNTAX INTEGER {
		fourMegabit(1),
		sixteenMegabit(2)
		}
	ACCESS read-write
	STATUS mandatory
	DESCRIPTION
		"The ring's bandwidth."
	::= { tnnPSBRGPortEntry 10 }


--
-- Trunk table is for compatibility purposes only
--

tnnPSBRGTrunkTable  OBJECT-TYPE
	SYNTAX SEQUENCE OF TnnPSBRGTrunkEntry
	ACCESS not-accessible
	STATUS mandatory
	DESCRIPTION
		"A table that contains trunk-specific information for
		each trunk on each tnnPS-BRG in the concentrator."
	::= {tnnPSBRG 3}

tnnPSBRGTrunkEntry  OBJECT-TYPE
	SYNTAX TnnPSBRGTrunkEntry
	ACCESS not-accessible
	STATUS mandatory
	DESCRIPTION
		"A list of information about a specific Trunk on a
		tnnPS-BRG module in the concentrator."
	INDEX {tnnPSBRGTrunkSlotIndex, tnnPSBRGTrunkIndex}
	::= {tnnPSBRGTrunkTable 1}

TnnPSBRGTrunkEntry ::=
	SEQUENCE {
		tnnPSBRGTrunkSlotIndex
			INTEGER,
		tnnPSBRGTrunkIndex
			INTEGER
		}

tnnPSBRGTrunkSlotIndex OBJECT-TYPE
	SYNTAX INTEGER
	ACCESS read-only
	STATUS mandatory
	DESCRIPTION
		"The slot number of this module. Its value ranges
		between 1 and concNumSlots."
	::= {tnnPSBRGTrunkEntry 1}

tnnPSBRGTrunkIndex OBJECT-TYPE
	SYNTAX INTEGER
	ACCESS read-only
	STATUS mandatory
	DESCRIPTION
		"The trunk number of this module. Its value ranges
		between 1 and modNumTrunks."
	::= {tnnPSBRGTrunkEntry 2}


--
-- Token ring management module
--

tnnMSMGTModTable  OBJECT-TYPE
	SYNTAX SEQUENCE OF TnnMSMGTModEntry
	ACCESS not-accessible
	STATUS mandatory
	DESCRIPTION
		"A table that contains module information about
		each tnnMS-MGT in the concentrator."
	::= {tnnMSMGT 1}

tnnMSMGTModEntry  OBJECT-TYPE
	SYNTAX TnnMSMGTModEntry
	ACCESS not-accessible
	STATUS mandatory
	DESCRIPTION
		"A list of module information for each tnnMS-MGT
		in the concentrator."
	INDEX {tnnMSMGTModSlotIndex}
	::= {tnnMSMGTModTable 1}

TnnMSMGTModEntry ::=
	SEQUENCE {
		tnnMSMGTModSlotIndex
			INTEGER,
		tnnMSMGTModMasterPriority
			INTEGER,
		tnnMSMGTModMasterStatus
			INTEGER,
		tnnMSMGTModStationAddr
			OCTET STRING,
		tnnMSMGTModRingSpeed
			INTEGER,
		tnnMSMGTModNetworkStatus
			INTEGER,
		tnnMSMGTModMasterNetwork
			INTEGER,
		tnnMSMGTModLocalMACAddress
			MacAddress,
		tnnMSMGTModMACAddressType
			INTEGER,
		tnnMSMGTModActiveMACAddress
			MacAddress
		}

tnnMSMGTModSlotIndex OBJECT-TYPE
	SYNTAX INTEGER
	ACCESS read-only
	STATUS mandatory
	DESCRIPTION
		"The slot number of this module. Its value ranges
		between 1 and concNumSlots."
	::= {tnnMSMGTModEntry 1}

tnnMSMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent. Ten is the
		highest and one is the lowest. Priority is only
		used when an election occurs. Mastership is not
		preemptive unless the reset mastership command is used."
	::= {tnnMSMGTModEntry 2}

tnnMSMGTModMasterStatus OBJECT-TYPE
	SYNTAX INTEGER {
		master(1),
		non-master(2),
		electing(3)
		}
	ACCESS read-only
	STATUS mandatory
	DESCRIPTION
		"The mastership status of this agent."
	::= {tnnMSMGTModEntry 3}

tnnMSMGTModStationAddr OBJECT-TYPE
	SYNTAX OCTET STRING
	ACCESS read-only
	STATUS mandatory
	DESCRIPTION
		"A 6 octet address that uniquely identifies this module.
		The station address is the MAC address of port 1."
	::= {tnnMSMGTModEntry 4}

tnnMSMGTModRingSpeed OBJECT-TYPE
	SYNTAX INTEGER {
		fourMegabit(1),
		sixteenMegabit(2)
		}
	ACCESS read-write
	STATUS mandatory
	DESCRIPTION
		"The ring's bandwidth."
	::= {tnnMSMGTModEntry 5}

tnnMSMGTModNetworkStatus OBJECT-TYPE
	SYNTAX INTEGER {
		okay(1),
		closed(2),
		beaconing(3)
		}
	ACCESS read-only
	STATUS mandatory
	DESCRIPTION
		"The status of the ring containing this module."
	::= {tnnMSMGTModEntry 6}

tnnMSMGTModMasterNetwork OBJECT-TYPE
	SYNTAX INTEGER {
		isolated(2),
		token-ring-1(9),
		token-ring-2(10),
		token-ring-3(11),
		token-ring-4(12),
		token-ring-5(13),
		token-ring-6(14),
		token-ring-7(15),
		no-change(25)
		}
	ACCESS read-write
	STATUS mandatory
	DESCRIPTION
		"The network that this module should assign itself to upon
		 becoming master if the module was previously a slave.
		 no-change(25) indicates that the module should not change
		 its current network assignment."
	::= {tnnMSMGTModEntry 7}


tnnMSMGTModLocalMACAddress OBJECT-TYPE
	SYNTAX MacAddress
	ACCESS read-write
	STATUS mandatory
	DESCRIPTION
		"A MAC address with the locally administered bit set to
		one. Setting this value to an invalid address will return
		invalidData error.  An invalid address is a value with the
		locally administered bit set to zero, or a value of all ones."
	::= {tnnMSMGTModEntry 8}


tnnMSMGTModMACAddressType OBJECT-TYPE
	SYNTAX INTEGER {
		burned-in(1),
		locally-administered(2)
		}
	ACCESS read-write
	STATUS mandatory
	DESCRIPTION
		"The desired MAC address for this agent.  burned-in(1)
		indicates that the factory setting as defined in
		tnnMSMGTModStationAddr should be used.
		locally-administered(2) indicates that the MAC address
		set in tnnMSMGTModLocalMACAddress should be used.  This
		change will take effect following a reset of the agent.
		The actual MAC address in use is defined in
		tnnMSMGTModActiveMACAddress.  Setting this value to use
		an invalid MAC address (for example, all zeros) will return
		invalidData error."
	::= {tnnMSMGTModEntry 9}

tnnMSMGTModActiveMACAddress OBJECT-TYPE
	SYNTAX MacAddress
	ACCESS read-only
	STATUS mandatory
	DESCRIPTION
		"A actual MAC address that is being used by this agent. This
		is the MAC address of port 1."
	::= {tnnMSMGTModEntry 10}

tnnMSMGTPortTable  OBJECT-TYPE
	SYNTAX SEQUENCE OF TnnMSMGTPortEntry
	ACCESS not-accessible
	STATUS mandatory
	DESCRIPTION
		"A table that contains port-specific information for
		each port on each tnnMS-MGT in the concentrator."
	::= {tnnMSMGT 2}

tnnMSMGTPortEntry  OBJECT-TYPE
	SYNTAX TnnMSMGTPortEntry
	ACCESS not-accessible
	STATUS mandatory
	DESCRIPTION
		"A list of information about a specific port on a
		tnnMS-MGT module in the concentrator."
	INDEX {tnnMSMGTPortSlotIndex, tnnMSMGTPortIndex}
	::= {tnnMSMGTPortTable 1}

TnnMSMGTPortEntry ::=
	SEQUENCE {
		tnnMSMGTPortSlotIndex
			INTEGER,
		tnnMSMGTPortIndex
			INTEGER,
		tnnMSMGTPortIpAddress
			IpAddress
		}

tnnMSMGTPortSlotIndex OBJECT-TYPE
	SYNTAX INTEGER
	ACCESS read-only
	STATUS mandatory
	DESCRIPTION
		"The slot number of this port's module."
	::= {tnnMSMGTPortEntry 1}

tnnMSMGTPortIndex OBJECT-TYPE
	SYNTAX INTEGER
	ACCESS read-only
	STATUS mandatory
	DESCRIPTION
		"The port number of this port."
	::= {tnnMSMGTPortEntry 2}

tnnMSMGTPortIpAddress  OBJECT-TYPE
	SYNTAX IpAddress
	ACCESS read-write
	STATUS mandatory
	DESCRIPTION
		"The IP address associated with this port."
	::= {tnnMSMGTPortEntry 3}

tnnMSMGTTrunkTable  OBJECT-TYPE
	SYNTAX SEQUENCE OF TnnMSMGTTrunkEntry
	ACCESS not-accessible
	STATUS mandatory
	DESCRIPTION
		"A table that contains trunk-specific information for
		each trunk on each tnnMS-MGT in the concentrator."
	::= {tnnMSMGT 3}

tnnMSMGTTrunkEntry  OBJECT-TYPE
	SYNTAX TnnMSMGTTrunkEntry
	ACCESS not-accessible
	STATUS mandatory
	DESCRIPTION
		"A list of information about a specific Trunk on a
		tnnMS-MGT module in the concentrator."
	INDEX {tnnMSMGTTrunkSlotIndex, tnnMSMGTTrunkIndex}
	::= {tnnMSMGTTrunkTable 1}

TnnMSMGTTrunkEntry ::=
	SEQUENCE {
		tnnMSMGTTrunkSlotIndex
			INTEGER,
		tnnMSMGTTrunkIndex
			INTEGER,
		tnnMSMGTTrunkCableMon
			INTEGER,
		tnnMSMGTTrunkNetMapState
			INTEGER,
		tnnMSMGTTrunkExtBcnRecovery
			INTEGER
		}

tnnMSMGTTrunkSlotIndex OBJECT-TYPE
	SYNTAX INTEGER
	ACCESS read-only
	STATUS mandatory
	DESCRIPTION
		"The slot number of this module. Its value ranges
		between 1 and concNumSlots."
	::= {tnnMSMGTTrunkEntry 1}

tnnMSMGTTrunkIndex OBJECT-TYPE
	SYNTAX INTEGER
	ACCESS read-only
	STATUS mandatory
	DESCRIPTION
		"The slot number of this module. Its value ranges
		between 1 and modNumTrunks."
	::= {tnnMSMGTTrunkEntry 2}

tnnMSMGTTrunkCableMon OBJECT-TYPE
	SYNTAX INTEGER {
		enable(1),
		disable(2),
		notApplicable(3)
		}
	ACCESS read-write
	STATUS mandatory
	DESCRIPTION
		"The cable monitor configuration for this trunk."
	::= {tnnMSMGTTrunkEntry 3}

tnnMSMGTTrunkNetMapState OBJECT-TYPE
	SYNTAX INTEGER {
		notApplicable(1),
		internal(2),
		external(3)
		}
	ACCESS read-write
	STATUS mandatory
	DESCRIPTION
		"The map state of the copper ring-in trunk. This
		should be set to external for ring-in trunks which
		connect to external hubs. The mapping logic will not
		operate on trunks which are set to external. This
		prevents incorrect mapping which can occur when a
		module in one hub detects the mapping signal from
		another hub. This attribute only applies to copper
		ring-in trunks."
	::= {tnnMSMGTTrunkEntry 4}


tnnMSMGTTrunkExtBcnRecovery OBJECT-TYPE
	SYNTAX INTEGER {
		exists(1),
		nonExists(2),
		notApplicable(3)
	}
	ACCESS read-write
	STATUS mandatory
	DESCRIPTION
		"Indicates whether the trunk is connected to a
		segment that will perform beacon recovery.  This
		should be set to exists(1) for trunks which connect
		to hubs which perform beacon recovery.  This attribute
		is used to determine the fault domain when resolving a
		beaconing condition.

		The beacon recovery process will resolve beaconing on
		trunks with this attribute set to nonExists(2) before
		trunks with the attribute set to exists(1) are resolved.
		For backplane trunks, setting to a value other than
		notApplicable will return invalidData error.  The
		default value is nonExists(2)."
	::= { tnnMSMGTTrunkEntry 5 }


--
-- Ethernet Interconnect Module
--

ee06PSBRGModTable OBJECT-TYPE
	SYNTAX SEQUENCE OF Ee06PSBRGModEntry
	ACCESS not-accessible
	STATUS mandatory
	DESCRIPTION
		"A table of module-specific information for
		each ee06PS-BRG module in the concentrator."
	::= { ee06PSBRG 1 }

ee06PSBRGModEntry OBJECT-TYPE
	SYNTAX Ee06PSBRGModEntry
	ACCESS not-accessible
	STATUS mandatory
	DESCRIPTION
		"A list of module-specific information about a specific
		ee06PS-BRG module in the concentrator."
	INDEX { ee06PSBRGModSlotIndex }
	::= { ee06PSBRGModTable 1 }

Ee06PSBRGModEntry ::=
	SEQUENCE {
		ee06PSBRGModSlotIndex
			INTEGER,
		ee06PSBRGModSwType
			INTEGER,
		ee06PSBRGModStationAddr
			OCTET STRING,
		ee06PSBRGModDipPromDefaults
			INTEGER,
		ee06PSBRGModProtocols
			DisplayString
		}

ee06PSBRGModSlotIndex OBJECT-TYPE
	SYNTAX INTEGER
	ACCESS read-only
	STATUS mandatory
	DESCRIPTION
		"The slot number of this module."
	::= { ee06PSBRGModEntry 1 }

ee06PSBRGModSwType OBJECT-TYPE
	SYNTAX INTEGER {
		bridge(1),
		switch(2),
		router(3)
		}
	ACCESS read-only
	STATUS mandatory
	DESCRIPTION
		"The software currently loaded and executing has the
		module operating as a Bridge, Switch or Router."
	::= { ee06PSBRGModEntry 2 }

ee06PSBRGModStationAddr OBJECT-TYPE
	SYNTAX OCTET STRING (SIZE(6))
	ACCESS read-only
	STATUS mandatory
	DESCRIPTION
		"A 6 octet address that uniquely identifies this module.
		The station address is the mac address of port 1."
	::= { ee06PSBRGModEntry 3 }

ee06PSBRGModDipPromDefaults OBJECT-TYPE
	SYNTAX INTEGER {
		true(1),
		false(2)
		}
	ACCESS read-only
	STATUS mandatory
	DESCRIPTION
		"The current module configuration with respect to
		default PROM values as specified by dip switches."
	::= { ee06PSBRGModEntry 4 }


ee06PSBRGModProtocols OBJECT-TYPE
	SYNTAX DisplayString
	ACCESS read-only
	STATUS mandatory
	DESCRIPTION
		"A textual description of the protocols supported by
		this module"
	::= { ee06PSBRGModEntry 5 }


ee06PSBRGPortTable	OBJECT-TYPE
	SYNTAX SEQUENCE OF Ee06PSBRGPortEntry
	ACCESS not-accessible
	STATUS mandatory
	DESCRIPTION
		"A table of port-specific information for each port of
		each ee06PS-BRG module in the concentrator."
	::= { ee06PSBRG 2 }


ee06PSBRGPortEntry OBJECT-TYPE
	SYNTAX Ee06PSBRGPortEntry
	ACCESS not-accessible
	STATUS mandatory
	DESCRIPTION
		"A list of port-specific information about a specific
		ee06PS-BRG port in the concentrator."
	INDEX { ee06PSBRGPortSlotIndex, ee06PSBRGPortIndex }
	::= { ee06PSBRGPortTable 1 }

Ee06PSBRGPortEntry ::=
	SEQUENCE {
		ee06PSBRGPortSlotIndex
			INTEGER,
		ee06PSBRGPortIndex
			INTEGER,
		ee06PSBRGPortDipAdminState
			INTEGER,
		ee06PSBRGPortSTAPState
			INTEGER,
		ee06PSBRGPortIpAddress
			IpAddress,
		ee06PSBRGPortDipNetwork
			INTEGER,
		ee06PSBRGPortDefNetwork
			INTEGER
		}

ee06PSBRGPortSlotIndex OBJECT-TYPE
	SYNTAX INTEGER
	ACCESS read-only
	STATUS mandatory
	DESCRIPTION
		"The slot number for this port's module."
	::= { ee06PSBRGPortEntry 1 }

ee06PSBRGPortIndex OBJECT-TYPE
	SYNTAX INTEGER
	ACCESS read-only
	STATUS mandatory
	DESCRIPTION
		"The port number for this port within this slot."
	::= { ee06PSBRGPortEntry 2 }

ee06PSBRGPortDipAdminState OBJECT-TYPE
	SYNTAX INTEGER {
		enabled(1),
		disabled(2)
		}
	ACCESS read-only
	STATUS mandatory
	DESCRIPTION
		"The state of this port as indicated by the port's dip
		switches."
	::= { ee06PSBRGPortEntry 3 }

ee06PSBRGPortSTAPState OBJECT-TYPE
	SYNTAX INTEGER {
		disabled (1),	-- receive and process frames
		blocking (2),	-- receive and process frames
		listening (3),  -- receive and process frames
		learning (4),	-- receive and process frames
		forwarding (5), -- receive, process and forward frames
		off (6),	-- receive SNMP frames, others discarded
		unknown(7)	-- not currently reporting STAP state
		}
	ACCESS read-only
	STATUS mandatory
	DESCRIPTION
		"The current IEEE 802.1d Spanning Tree Algorithm and Protocol
		 state (STAP) of this port."
	::= { ee06PSBRGPortEntry 4 }

ee06PSBRGPortIpAddress OBJECT-TYPE
	SYNTAX IpAddress
	ACCESS read-only
	STATUS mandatory
	DESCRIPTION
		"The IP Address associated with this port."
	::= { ee06PSBRGPortEntry 5 }

ee06PSBRGPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ee06PSBRGPortEntry 6 }

ee06PSBRGPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OEIM's
		non-volatile storage."
	::= { ee06PSBRGPortEntry 7 }


--
-- FDDI Management Module
--

fnnMSMGTModTable OBJECT-TYPE
	SYNTAX SEQUENCE OF FnnMSMGTModEntry
	ACCESS not-accessible
	STATUS mandatory
	DESCRIPTION
		"A list of module attributes that apply to this model.
		To access an fnnMSMGTModTable entry, the
		fnnMSMGTModSlotIndex attribute is used."
	::= { fnnMSMGT 1 }

fnnMSMGTModEntry OBJECT-TYPE
	SYNTAX FnnMSMGTModEntry
	ACCESS not-accessible
	STATUS mandatory
	DESCRIPTION
		"A list of module-specific information about a specific
		fnnMS-MGT module in the concentrator."
	INDEX { fnnMSMGTModSlotIndex }
	::= { fnnMSMGTModTable 1 }

FnnMSMGTModEntry ::=
	SEQUENCE {
		fnnMSMGTModSlotIndex
			INTEGER,
		fnnMSMGTModMasterPriority
			INTEGER,
		fnnMSMGTModMasterStatus
			INTEGER,
		fnnMSMGTModStationAddr
			OCTET STRING,
		fnnMSMGTModIpAddress
			IpAddress,
		fnnMSMGTModDownStreamMAC
			OCTET STRING,
		fnnMSMGTModUpStreamMAC
			OCTET STRING,
		fnnMSMGTModfddiMACPath
			INTEGER,
		fnnMSMGTModDownStreamModule
			INTEGER,
		fnnMSMGTModUpStreamModule
			INTEGER,
		fnnMSMGTModDownStreamOperPath
			INTEGER,
		fnnMSMGTModUpStreamOperPath
			INTEGER,
		fnnMSMGTModRingInfo
			OCTET STRING
		}

fnnMSMGTModSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of modSlotIndex."
	::= { fnnMSMGTModEntry 1 }

fnnMSMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent. Ten is the
		highest and one is the lowest. Priority is only
		used when an election occurs. Mastership is not
		preemptive unless the reset mastership command is used."
	::= {fnnMSMGTModEntry 2 }

fnnMSMGTModMasterStatus OBJECT-TYPE
	SYNTAX INTEGER {
		master(1),
		non-master(2),
		electing(3)
		}
	ACCESS read-only
	STATUS mandatory
	DESCRIPTION
		"The mastership status of this agent."
	::= {fnnMSMGTModEntry 3 }

fnnMSMGTModStationAddr OBJECT-TYPE
	SYNTAX OCTET STRING (SIZE (6))
	ACCESS read-only
	STATUS mandatory
	DESCRIPTION
		"A 6 octet address that uniquely identifies this module.
		The station address is the MAC address of port 1."
	::= {fnnMSMGTModEntry 4 }

fnnMSMGTModIpAddress  OBJECT-TYPE
	SYNTAX IpAddress
	ACCESS read-only
	STATUS mandatory
	DESCRIPTION
		"The IP address associated with this module."
	::= {fnnMSMGTModEntry 5 }

fnnMSMGTModDownStreamMAC OBJECT-TYPE
	SYNTAX OCTET STRING (SIZE (6))
	ACCESS read-only
	STATUS mandatory
	DESCRIPTION
		"Down stream MAC"
	::= { fnnMSMGTModEntry 6 }

fnnMSMGTModUpStreamMAC OBJECT-TYPE
	SYNTAX OCTET STRING (SIZE (6))
	ACCESS read-only
	STATUS mandatory
	DESCRIPTION
		"Up stream MAC"
	::= { fnnMSMGTModEntry 7 }

fnnMSMGTModfddiMACPath OBJECT-TYPE
	SYNTAX INTEGER {
		primary(1),
		secondary(2)
		}
	ACCESS read-write
	STATUS mandatory
	DESCRIPTION
		"The FDDI path which should be inserted into the MAC"
	::= { fnnMSMGTModEntry 8 }

fnnMSMGTModDownStreamModule OBJECT-TYPE
	SYNTAX INTEGER (1..16)
	ACCESS read-only
	STATUS mandatory
	DESCRIPTION
		"Down stream slot (transmit to)"
	::= { fnnMSMGTModEntry 9 }

fnnMSMGTModUpStreamModule OBJECT-TYPE
	SYNTAX INTEGER (1..16)
	ACCESS read-only
	STATUS mandatory
	DESCRIPTION
		"Up stream slot (receive from)"
	::= { fnnMSMGTModEntry 10 }

fnnMSMGTModDownStreamOperPath OBJECT-TYPE
	SYNTAX INTEGER {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"Transmit DBA  (debug only)"
	::= { fnnMSMGTModEntry 11 }

fnnMSMGTModUpStreamOperPath OBJECT-TYPE
	SYNTAX INTEGER  {
		isolated(2),
		fddi-path-1(24),
		fddi-path-2(25),
		fddi-path-3(26),
		fddi-path-4(27),
		fddi-path-5(28),
		fddi-path-6(29),
		fddi-path-7(30),
		fddi-path-8(31)
		}
	ACCESS read-only
	STATUS mandatory
	DESCRIPTION
		"Receive DBA (debug only)"
	::= { fnnMSMGTModEntry 12 }

fnnMSMGTModRingInfo OBJECT-TYPE
	SYNTAX OCTET STRING (SIZE(1..8))
	ACCESS read-only
	STATUS mandatory
	DESCRIPTION
		"An array which is indexed by DBA number. Each element
		 contains the slot number (1..16) which is assigned to
		 transmit on this DBA. (debug only)"
	::= { fnnMSMGTModEntry 13 }


-- port table

fnnMSMGTPortTable OBJECT-TYPE
	SYNTAX SEQUENCE OF FnnMSMGTPortEntry
	ACCESS not-accessible
	STATUS mandatory
	DESCRIPTION
		"A table of port-specific information for each port of
		this module type."
	::= { fnnMSMGT 2 }

fnnMSMGTPortEntry OBJECT-TYPE
	SYNTAX FnnMSMGTPortEntry
	ACCESS not-accessible
	STATUS mandatory
	DESCRIPTION
		"A list of module-specific information about a specific
		fnnMS-MGT port in the concentrator."
	INDEX { fnnMSMGTPortSlotIndex, fnnMSMGTPortIndex }
	::= { fnnMSMGTPortTable 1 }

FnnMSMGTPortEntry ::=
	SEQUENCE {
		fnnMSMGTPortSlotIndex
			INTEGER,
		fnnMSMGTPortIndex
			INTEGER,
		fnnMSMGTPortConfig
			INTEGER,
		fnnMSMGTPortPcmState
			INTEGER,
		fnnMSMGTPortConnectState
			INTEGER,
		fnnMSMGTPortNeighbor
			INTEGER,
		fnnMSMGTPortRemoteMACIndicated
			INTEGER,
		fnnMSMGTPortBSFlag
			INTEGER,
		fnnMSMGTPortPCWithhold
			INTEGER,
		fnnMSMGTPortLerCondition
			INTEGER
		}

fnnMSMGTPortSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		portSlotIndex."
	::= { fnnMSMGTPortEntry 1 }


fnnMSMGTPortIndex OBJECT-TYPE
	SYNTAX INTEGER
	ACCESS read-only
	STATUS mandatory
	DESCRIPTION
		"A unique value that identifies a particular port within this
		module. Its value ranges between 1 and modPortNumber.
		The module identified by a particular value of this index is
		the same module as indentified by the same value of
		portIndex."
	::= { fnnMSMGTPortEntry 2 }

fnnMSMGTPortConfig OBJECT-TYPE
	SYNTAX INTEGER {
		a(1),
		b(2)
		}
	ACCESS read-only
	STATUS mandatory
	DESCRIPTION
		"Specifies the FDDI port type (a or b)."
	::= { fnnMSMGTPortEntry 3 }

fnnMSMGTPortPcmState OBJECT-TYPE
	SYNTAX INTEGER {
		  pc0(1), -- Off
		  pc1(2), -- Break
		  pc2(3), -- Trace
		  pc3(4), -- Connect
		  pc4(5), -- Next
		  pc5(6), -- Signal
		  pc6(7), -- Join
		  pc7(8), -- Verify
		  pc8(9), -- Active
		  pc9(10) -- Maint
	}
	ACCESS read-only
	STATUS mandatory
	DESCRIPTION
		      "(refer to ANSI SMT 9.6.2)."
	::= { fnnMSMGTPortEntry 4 }

fnnMSMGTPortConnectState OBJECT-TYPE
	SYNTAX INTEGER {
	  disabled(1),
	  connecting(2),
	  standby(3),
	  active(4)
		}
	ACCESS read-only
	STATUS mandatory
	DESCRIPTION
	     "An indication of the connect state of this PORT.
	      Basically, this gives a higher level view of the
	      state of the connection by grouping PCM states and
	      the PC-Withhold flag state.  The supported values
	      and their corresponding PCM states and PC-Withhold
	      condition, when relevant, are:
		  disabled: (PC0:Off, PC9:Maint)
		  connecting: (PC1(Break) || PC3 (Connect) || PC4(next) ||
			       PC5 (Signal) || PC6(Join) || PC7 (Verify)) &&
			      (PC_Withhold = None)
		  standby: (PC_Withhold != None)
		  active: (PC2:Trace || PC8:Active)"
	::= { fnnMSMGTPortEntry 5 }

fnnMSMGTPortNeighbor OBJECT-TYPE
	SYNTAX INTEGER {
		a(1),
		b(2),
		slave(3),
		master(4),
		unknown(5)
		}
	ACCESS read-only
	STATUS mandatory
	DESCRIPTION
	     "The type (PC_Neighbor) of the remote PORT that is
	      determined in PC_Signaling in R_Val (1,2) (refer
	      to ANSI SMT 9.6.3.2)."
	::= { fnnMSMGTPortEntry 6 }

fnnMSMGTPortRemoteMACIndicated OBJECT-TYPE
	SYNTAX INTEGER { true(1), false(2) }
	ACCESS read-only
	STATUS mandatory
	DESCRIPTION
	  "The indication, in PC-Signaling that the remote
	   partner intends to place a MAC in the output token
	   PATH of this PORT.  Signaled as R_Val (9) (refer
	   to ANSI SMT 9.6.3.2)."
	::= { fnnMSMGTPortEntry 7 }

fnnMSMGTPortBSFlag OBJECT-TYPE
	SYNTAX INTEGER { true(1), false(2) }
	ACCESS read-only
	STATUS mandatory
	DESCRIPTION
	  "The Break State, BS_Flag (refer to ANSI SMT
	   9.4.3.4)."
	::= { fnnMSMGTPortEntry 8 }

fnnMSMGTPortPCWithhold OBJECT-TYPE
	SYNTAX INTEGER  { none(1), m-m(2), other(3) }
	ACCESS read-only
	STATUS mandatory
	DESCRIPTION
	   "PC_Withhold, (refer to ANSI SMT 9.4.1)."
	::= { fnnMSMGTPortEntry 9 }

fnnMSMGTPortLerCondition OBJECT-TYPE
	SYNTAX INTEGER  { bad(1), okay(2) }
	ACCESS read-only
	STATUS mandatory
	DESCRIPTION
	   "This variable is set to true whenever LerEstimate
	    is less than or equal to LerAlarm (the larger the number
	    the smaller the value)."
	::= { fnnMSMGTPortEntry 10 }


-- Trunk Table
-- (only present for compatibility)

fnnMSMGTTrunkTable OBJECT-TYPE
	SYNTAX SEQUENCE OF FnnMSMGTTrunkEntry
	ACCESS not-accessible
	STATUS mandatory
	DESCRIPTION
		"FDDI module specific trunk table variables.
		 At present there are none."
	::= { fnnMSMGT 3 }

fnnMSMGTTrunkEntry OBJECT-TYPE
	SYNTAX FnnMSMGTTrunkEntry
	ACCESS not-accessible
	STATUS mandatory
	DESCRIPTION
		"A description of fnnMS-MGT trunk attributes."
	INDEX { fnnMSMGTTrunkSlotIndex, fnnMSMGTTrunkIndex }
	::= { fnnMSMGTTrunkTable 1 }

FnnMSMGTTrunkEntry ::=
	SEQUENCE {
		fnnMSMGTTrunkSlotIndex
			INTEGER,
		fnnMSMGTTrunkIndex
			INTEGER
		}

fnnMSMGTTrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { fnnMSMGTTrunkEntry 1 }


fnnMSMGTTrunkIndex OBJECT-TYPE
	SYNTAX INTEGER
	ACCESS read-only
	STATUS mandatory
	DESCRIPTION
		"A unique value that identifies a particular trunk within this
		module. Its value ranges between 1 and modTrunkNumber.
		The module identified by a particular value of this index is
		the same module as indentified by the same value of
		trunkIndex."
	::= { fnnMSMGTTrunkEntry 2 }


--
-- Hub Hidden Controller Module
--

cnnNSHCTLModTable OBJECT-TYPE
	SYNTAX SEQUENCE OF CnnNSHCTLModEntry
	ACCESS not-accessible
	STATUS mandatory
	DESCRIPTION
		"A table that contains information about each cnnNS-HCTL
		in the concentrator.  "
	::= { cnnNSHCTL 1 }

cnnNSHCTLModEntry OBJECT-TYPE
	SYNTAX CnnNSHCTLModEntry
	ACCESS not-accessible
	STATUS mandatory
	DESCRIPTION
		"A list of information for each cnnNS-HCTL module
		in the concentrator."
	INDEX { cnnNSHCTLModSlotIndex }
	::= { cnnNSHCTLModTable 1 }

CnnNSHCTLModEntry ::=
	SEQUENCE {
		cnnNSHCTLModSlotIndex
			INTEGER,
		cnnNSHCTLModOperState
			INTEGER,
		cnnNSHCTLModClockStatus
			INTEGER,
		cnnNSHCTLModTempStatus
			INTEGER,
		cnnNSHCTLModPDBStatus
			INTEGER,
		cnnNSHCTLModDipCh1ActCol
			INTEGER,
		cnnNSHCTLModDipCh2ActCol
			INTEGER,
		cnnNSHCTLModDipCh3ActCol
			INTEGER
		}

cnnNSHCTLModSlotIndex OBJECT-TYPE
	SYNTAX INTEGER
	ACCESS read-only
	STATUS mandatory
	DESCRIPTION
		"The slot number for this module.  The value should be 7."
	::= { cnnNSHCTLModEntry 1 }

cnnNSHCTLModOperState OBJECT-TYPE
	SYNTAX INTEGER {
		active(1),
		standby(2)
		}
	ACCESS read-only
	STATUS mandatory
	DESCRIPTION
		"The operational state of the cnnNS-HCTL module.  Specifically,
		this is an indicator of whether the cnnNS-HCTL module is
		providing clock signals to the backplane.  An active cnnNS-HCTL
		module provides clock signals to the backplane while a standby
		cnnNS-HCTL module does not.  Note that only one cnnNS-HCTL
		module will be active at any given time; all other cnnNS-HCTL/
		cnnNS-RCTL modules in the concentrator will be in standby mode."
	::= { cnnNSHCTLModEntry 2 }

cnnNSHCTLModClockStatus OBJECT-TYPE
	SYNTAX INTEGER {
		okay(1),
		faulty(2)
		}
	ACCESS read-only
	STATUS mandatory
	DESCRIPTION
		"The current status of the on-board clocks on this module."
	::= { cnnNSHCTLModEntry 3 }

cnnNSHCTLModTempStatus OBJECT-TYPE
	SYNTAX INTEGER {
		okay(1),
		extremeTemp(2)
		}
	ACCESS read-only
	STATUS mandatory
	DESCRIPTION
		"The temperature as detected by the probe on this module."
	::= { cnnNSHCTLModEntry 4 }

cnnNSHCTLModPDBStatus OBJECT-TYPE
	SYNTAX INTEGER {
		present(1),
		notPresent(2)
		}
	ACCESS read-only
	STATUS mandatory
	DESCRIPTION
		"Indicates whether this 6-slot concentrator contains a power
		distribution board that supports powersupply redundancy."
	::= { cnnNSHCTLModEntry 5 }

cnnNSHCTLModDipCh1ActCol OBJECT-TYPE
	SYNTAX INTEGER {
		enabled(1),
		disabled(2)
		}
	ACCESS read-only
	STATUS mandatory
	DESCRIPTION
		"The Ethernet channel 1 activity/collision LED configuration
		as indicated by this module's dip switches."
	::= { cnnNSHCTLModEntry 6 }

cnnNSHCTLModDipCh2ActCol OBJECT-TYPE
	SYNTAX INTEGER {
		enabled(1),
		disabled(2)
		}
	ACCESS read-only
	STATUS mandatory
	DESCRIPTION
		"The Ethernet channel 2 activity/collision LED configuration
		as indicated by this module's dip switches."
	::= { cnnNSHCTLModEntry 7 }

cnnNSHCTLModDipCh3ActCol OBJECT-TYPE
	SYNTAX INTEGER {
		enabled(1),
		disabled(2)
		}
	ACCESS read-only
	STATUS mandatory
	DESCRIPTION
		"The Ethernet channel 3 activity/collision LED configuration
		as indicated by this module's dip switches."
	::= { cnnNSHCTLModEntry 8 }


--
-- Hub Load Sharing Redundant Controller Module
--

cnnNSRCLSModTable OBJECT-TYPE
	SYNTAX SEQUENCE OF CnnNSRCLSModEntry
	ACCESS not-accessible
	STATUS mandatory
	DESCRIPTION
		"A table that contains information about each Redundant
		Controller in the concentrator."
	::= { cnnNSRCLS 1 }

cnnNSRCLSModEntry OBJECT-TYPE
	SYNTAX CnnNSRCLSModEntry
	ACCESS not-accessible
	STATUS mandatory
	DESCRIPTION
		"A list of information for each Load Sharing Redundant
		 controller module in the concentrator."
	INDEX { cnnNSRCLSModSlotIndex }
	::= { cnnNSRCLSModTable 1 }

CnnNSRCLSModEntry ::=
	SEQUENCE {
		cnnNSRCLSModSlotIndex
			INTEGER,
		cnnNSRCLSModOperState
			INTEGER,
		cnnNSRCLSModClockStatus
			INTEGER,
		cnnNSRCLSModTempStatus
			INTEGER
		}

cnnNSRCLSModSlotIndex OBJECT-TYPE
	SYNTAX INTEGER
	ACCESS read-only
	STATUS mandatory
	DESCRIPTION
		"The slot number for this module."
	::= { cnnNSRCLSModEntry 1 }

cnnNSRCLSModOperState OBJECT-TYPE
	SYNTAX INTEGER {
		active(1),
		standby(2)
		}
	ACCESS read-only
	STATUS mandatory
	DESCRIPTION
		"The operational state of the Load Sharing Redudant Controller
		module.  Specifically, this is an indicator of whether the
		Load Sharing Redudant Controller module is providing clock
		signals to the backplane.  An active Load Sharing Redudant
		Controller module provides clock signals to the backplane
		while a standby Load Sharing Redudant Controller module does
		not.  Note that only one Load Sharing Redudant Controller
		module will be active at any given time; all other
		Load Sharing Redudant Controller modules in the concentrator
		will be in standby mode."
	::= { cnnNSRCLSModEntry 2 }

cnnNSRCLSModClockStatus OBJECT-TYPE
	SYNTAX INTEGER {
		okay(1),
		faulty(2)
		}
	ACCESS read-only
	STATUS mandatory
	DESCRIPTION
		"The current status of the on-board clocks on this module."
	::= { cnnNSRCLSModEntry 3 }

cnnNSRCLSModTempStatus OBJECT-TYPE
	SYNTAX INTEGER {
		okay(1),
		extremeTemp(2)
		}
	ACCESS read-only
	STATUS mandatory
	DESCRIPTION
		"The temperature as detected by the probe on this module."
	::= { cnnNSRCLSModEntry 4 }


--
-- Ethernet 10BASE-T Security Module (OESM)
--

ennMSSTELCOModTable OBJECT-TYPE
	SYNTAX SEQUENCE OF EnnMSSTELCOModEntry
	ACCESS not-accessible
	STATUS mandatory
	DESCRIPTION
		"A list of module-specific information about a specific
		ennMS-TELCOS module in the concentrator."
	::= { ennMSSTELCO 1 }

ennMSSTELCOModEntry OBJECT-TYPE
	SYNTAX EnnMSSTELCOModEntry
	ACCESS not-accessible
	STATUS mandatory
	DESCRIPTION
		"A list of module-specific information about a specific
		ennMS-TELCOS module in the concentrator."
	INDEX { ennMSSTELCOModSlotIndex }
	::= { ennMSSTELCOModTable 1 }

EnnMSSTELCOModEntry ::=
	SEQUENCE {
		ennMSSTELCOModSlotIndex
			INTEGER,
		ennMSSTELCOModDipNetwork
			INTEGER,
		ennMSSTELCOModAutoPartition
			INTEGER
		}

ennMSSTELCOModSlotIndex OBJECT-TYPE
	SYNTAX INTEGER
	ACCESS read-only
	STATUS mandatory
	DESCRIPTION
		"The slot number of this module."
	::= { ennMSSTELCOModEntry 1 }

ennMSSTELCOModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ennMSSTELCOModEntry 2 }

ennMSSTELCOModAutoPartition OBJECT-TYPE
	SYNTAX INTEGER {
		collisions-31(1),
		collisions-63(2),
		collisions-127(3),
		collisions-255(4)
		}
	ACCESS read-write
	STATUS mandatory
	DESCRIPTION
		"This object holds the consecutive collision count
		 limit value.  The module goes into the auto-partition
		 mode whenever the consecutive collision count exceeds
		 this limit."
	::= { ennMSSTELCOModEntry 3 }

ennMSSTELCOPortTable OBJECT-TYPE
	SYNTAX SEQUENCE OF EnnMSSTELCOPortEntry
	ACCESS not-accessible
	STATUS mandatory
	DESCRIPTION
		"A table of port-specific information for each port of
		this module type."
	::= { ennMSSTELCO 2 }

ennMSSTELCOPortEntry OBJECT-TYPE
	SYNTAX EnnMSSTELCOPortEntry
	ACCESS not-accessible
	STATUS mandatory
	DESCRIPTION
		"A list of module-specific information about a specific
		ennMS-TELCOS port in the concentrator."
	INDEX { ennMSSTELCOPortSlotIndex, ennMSSTELCOPortIndex }
	::= { ennMSSTELCOPortTable 1 }

EnnMSSTELCOPortEntry ::=
	SEQUENCE {
		ennMSSTELCOPortSlotIndex
			INTEGER,
		ennMSSTELCOPortIndex
			INTEGER,
		ennMSSTELCOPortAdminState
			INTEGER,
		ennMSSTELCOPortDipAdminState
			INTEGER,
		ennMSSTELCOPortDipSecurity
			INTEGER,
		ennMSSTELCOPortBuddySlot
			INTEGER,
		ennMSSTELCOPortBuddyPort
			INTEGER,
		ennMSSTELCOPortLinkInteg
			INTEGER,
		ennMSSTELCOPortDipLinkInteg
			INTEGER
		}

ennMSSTELCOPortSlotIndex OBJECT-TYPE
	SYNTAX INTEGER
	ACCESS read-only
	STATUS mandatory
	DESCRIPTION
		"The slot number of this port's module."
	::= { ennMSSTELCOPortEntry 1 }


ennMSSTELCOPortIndex OBJECT-TYPE
	SYNTAX INTEGER
	ACCESS read-only
	STATUS mandatory
	DESCRIPTION
		"The port number of this port."
	::= { ennMSSTELCOPortEntry 2 }

ennMSSTELCOPortAdminState OBJECT-TYPE
	SYNTAX INTEGER {
		enabled(1),
		disabled(2),
		redundant-primary(3),
		redundant-backup(4),
		remote-diagnostics(8)
		}
	ACCESS read-write
	STATUS mandatory
	DESCRIPTION
		"The desired state of this port.  Setting this port to
		be redundant or for remote diagnostics with invalid settings
		of buddy slot and buddy port will return the genError error."
	::= { ennMSSTELCOPortEntry 3 }

ennMSSTELCOPortDipAdminState OBJECT-TYPE
	SYNTAX INTEGER {
		enabled(1),
		disabled(2)
		}
	ACCESS read-write
	STATUS mandatory
	DESCRIPTION
		"The admin state of this port as indicated by the dip
		switches.  i.e. This object indicates whether the port
		will initialize to enabled or disabled when the module
		configures itself from dips."
	::= { ennMSSTELCOPortEntry 4 }

ennMSSTELCOPortDipSecurity OBJECT-TYPE
	SYNTAX INTEGER {
		enabled(1),
		disabled(2)
		}
	ACCESS read-only
	STATUS mandatory
	DESCRIPTION
		"The security state of this port as indicated by the dip
		switches.  i.e. This object indicates whether the port's
		security state will initialize to enabled (full security)
		or disabled (no security) when the module configures itself
		from dips."
	::= { ennMSSTELCOPortEntry 5 }

ennMSSTELCOPortBuddySlot OBJECT-TYPE
	SYNTAX INTEGER
	ACCESS read-write
	STATUS mandatory
	DESCRIPTION
		"The slot index of the redundant port's buddy.  To set
		a port to be redundant, the buddy's slot and port must
		be set to valid values.

		The buddy is automatically set to be redundant to this port.

		If the port is configured for remote diagnostics, then
		this contains the slot index of the backup buddy port.
		To configure a port for remote diagnostics, the buddy's
		slot and port must be set to valid values."
	::= { ennMSSTELCOPortEntry 6 }

ennMSSTELCOPortBuddyPort  OBJECT-TYPE
	SYNTAX INTEGER
	ACCESS read-write
	STATUS mandatory
	DESCRIPTION
		"The port index of the redundant port's buddy.  To set
		a port to be redundant, the buddy's slot and port must
		be set to valid values.

		The buddy is automatically set to be redundant to this port.

		If the port is configured for remote diagnostics, then
		this contains the port index of the backup buddy port.
		To configure a port for remote diagnostics, the buddy's
		slot and port must be set to valid values."
	::= { ennMSSTELCOPortEntry 7 }

ennMSSTELCOPortLinkInteg OBJECT-TYPE
	SYNTAX INTEGER {
		enabled(1),
		disabled(2)
		}
	ACCESS read-write
	STATUS mandatory
	DESCRIPTION
		"The current link integrity configuration for this port."
	::= { ennMSSTELCOPortEntry 8 }

ennMSSTELCOPortDipLinkInteg OBJECT-TYPE
	SYNTAX INTEGER {
		enabled(1),
		disabled(2)
		}
	ACCESS read-only
	STATUS mandatory
	DESCRIPTION
		"The link integrity configuration as indicated by this
		module's dip switches."
	::= { ennMSSTELCOPortEntry 9 }


--
-- IBM 8260 Ethernet 10BASE-T Per-Port Module
--

e24PS6PortTable			 OBJECT-TYPE
	SYNTAX SEQUENCE OF E24PS6PortEntry
	ACCESS not-accessible
	STATUS mandatory
	DESCRIPTION
		"A table of port-specific information for each port of
		this module type."
	::= { e24PS6 2 }

e24PS6PortEntry OBJECT-TYPE
	SYNTAX E24PS6PortEntry
	ACCESS not-accessible
	STATUS mandatory
	DESCRIPTION
		"A list of module-specific information about a specific
		E24PS-6 port in the concentrator."
	INDEX { e24PS6PortSlotIndex, e24PS6PortIndex }
	::= { e24PS6PortTable 1 }

E24PS6PortEntry ::=
	SEQUENCE {
		e24PS6PortSlotIndex
			INTEGER,
		e24PS6PortIndex
			INTEGER,
		e24PS6PortAdminState
			INTEGER,
		e24PS6PortBuddySlot
			INTEGER,
		e24PS6PortBuddyPort
			INTEGER,
		e24PS6PortDipNetwork
			INTEGER,
		e24PS6PortLinkInteg
			INTEGER,
		e24PS6PortAutoPolarity
			INTEGER

		}

e24PS6PortSlotIndex OBJECT-TYPE
	 SYNTAX INTEGER
	 ACCESS read-only
	 STATUS mandatory
	 DESCRIPTION
		 "The slot number of this port's module."
	 ::= { e24PS6PortEntry 1 }


e24PS6PortIndex OBJECT-TYPE
	 SYNTAX INTEGER
	 ACCESS read-only
	 STATUS mandatory
	 DESCRIPTION
		 "The port number of this port."
	 ::= { e24PS6PortEntry 2 }

e24PS6PortAdminState OBJECT-TYPE
	 SYNTAX INTEGER {
		 enabled(1),
		 disabled(2),
		 redundant-primary(3),
		 redundant-backup(4),
		 remote-diagnostics(8)
		 }
	 ACCESS read-write
	 STATUS mandatory
	 DESCRIPTION
		 "The desired state of this port.  Setting this port to
		 be redundant or for remote diagnostics with invalid settings
		 of buddy slot and buddy port will return the genError error."
	 ::= { e24PS6PortEntry 3 }

e24PS6PortBuddySlot OBJECT-TYPE
	 SYNTAX INTEGER
	 ACCESS read-write
	 STATUS mandatory
	 DESCRIPTION
		 "The slot index of the redundant port's buddy.  To set
		 a port to be redundant, the buddy's slot and port must
		 be set to valid values.

		 The buddy is automatically set to be redundant to this port.

		 If the port is configured for remote diagnostics, then
		 this contains the slot index of the backup buddy port.
		 To configure a port for remote diagnostics, the buddy's
		 slot and port must be set to valid values."

	 ::= { e24PS6PortEntry 4 }

e24PS6PortBuddyPort  OBJECT-TYPE
	 SYNTAX INTEGER
	 ACCESS read-write
	 STATUS mandatory
	 DESCRIPTION
		 "The port index of the redundant port's buddy.  To set
		 a port to be redundant, the buddy's slot and port must
		 be set to valid values.

		 The buddy is automatically set to be redundant to this port.

		 If the port is configured for remote diagnostics, then
		 this contains the port index of the backup buddy port.
		 To configure a port for remote diagnostics, the buddy's
		 slot and port must be set to valid values."
	 ::= { e24PS6PortEntry 5 }

e24PS6PortDipNetwork OBJECT-TYPE
	 SYNTAX INTEGER {
		 ethernet-1(6),
		 ethernet-2(7),
		 ethernet-3(8),
		 isolated-1(21),
		 ethernet-4(32),	-- IBM 8260 networks : --
		 ethernet-5(33),
		 ethernet-6(34),
		 ethernet-7(35),
		 ethernet-8(36)
		 }
	 ACCESS read-only
	 STATUS mandatory
	 DESCRIPTION
		 "The network indicated by the port's dip switches."
	 ::= { e24PS6PortEntry 6 }

e24PS6PortLinkInteg OBJECT-TYPE
	 SYNTAX INTEGER {
		 enabled(1),
		 disabled(2)
		 }
	 ACCESS read-write
	 STATUS mandatory
	 DESCRIPTION
		 "The current link integrity configuration for this
		  port.  Setting this object to enabled(1) makes it
		  conform to the 10BASE-T link integrity standard.
		  Setting this object to disabled(2) makes it compatible
		  with the older pre 10BASE-T module."
	 ::= { e24PS6PortEntry 7 }

e24PS6PortAutoPolarity OBJECT-TYPE
	 SYNTAX INTEGER {
		 enabled(1),
		 disabled(2)
		 }
	 ACCESS read-write
	 STATUS mandatory
	 DESCRIPTION
		 "The current auto polarity configuration for this port.
		  Setting this object to enabled(1) causes the module to
		  switch the port polarity automatically when the port
		  polarity is reverted."
	 ::= { e24PS6PortEntry 8 }


e24PS6ModTable OBJECT-TYPE
	SYNTAX SEQUENCE OF E24PS6ModEntry
	ACCESS not-accessible
	STATUS mandatory
	DESCRIPTION
		"A list of module-specific information about a specific
		E24PS-6 module in the concentrator."
	::= { e24PS6 6 }

e24PS6ModEntry OBJECT-TYPE
	SYNTAX E24PS6ModEntry
	ACCESS not-accessible
	STATUS mandatory
	DESCRIPTION
		"A list of module-specific information about a specific
		E24PS-6 module in the concentrator."
	INDEX { e24PS6ModSlotIndex, e24PS6ModSubSlotIndex }
	::= { e24PS6ModTable 1 }

E24PS6ModEntry ::=
	SEQUENCE {
		e24PS6ModSlotIndex
			INTEGER,
		e24PS6ModSubSlotIndex
			INTEGER,
		e24PS6ModBootVersion
			DisplayString,
		e24PS6ModDipNVRam
			INTEGER
		}

e24PS6ModSlotIndex OBJECT-TYPE
	SYNTAX INTEGER
	ACCESS read-only
	STATUS mandatory
	DESCRIPTION
		"The slot number of this module."
	::= { e24PS6ModEntry 1 }

e24PS6ModSubSlotIndex OBJECT-TYPE
	SYNTAX INTEGER
	ACCESS read-only
	STATUS mandatory
	DESCRIPTION
		"The subslot number of this module."
	::= { e24PS6ModEntry 2 }

e24PS6ModBootVersion OBJECT-TYPE
	SYNTAX DisplayString (SIZE(1..32))
	ACCESS read-only
	STATUS mandatory
	DESCRIPTION
		"The software boot eprom version of this module.  "
	::= { e24PS6ModEntry 3 }

e24PS6ModDipNVRam OBJECT-TYPE
	SYNTAX INTEGER {
	enabled(1),
	disabled(2)
	}
	ACCESS read-only
	STATUS mandatory
	DESCRIPTION
		"The Non-Volatile RAM dip switch setting for this
		 module.  Enabling this switch will cause the module
		 to be configured according to the configurations that
		 were saved in the non-volatile storage after the
		 module reset."
	::= { e24PS6ModEntry 4 }


--
-- IBM 8260 Ethernet Carrier Module
--
eCModTable OBJECT-TYPE
	SYNTAX SEQUENCE OF ECModEntry
	ACCESS not-accessible
	STATUS mandatory
	DESCRIPTION
		"A list of module-specific information associated
		with a particular EC module in the concentrator."
	::= { eC 6 }

eCModEntry OBJECT-TYPE
	SYNTAX ECModEntry
	ACCESS not-accessible
	STATUS mandatory
	DESCRIPTION
		"A list of module-specific information about a specific
		EC module in the concentrator."
	INDEX { eCModSlotIndex, eCModSubSlotIndex }
	::= { eCModTable 1 }

ECModEntry ::=
	SEQUENCE {
		eCModSlotIndex
			INTEGER,
		eCModSubSlotIndex
			INTEGER,
		eCModBootVersion
			DisplayString
		}

eCModSlotIndex OBJECT-TYPE
	SYNTAX INTEGER
	ACCESS read-only
	STATUS mandatory
	DESCRIPTION
		"The slot number of this module."
	::= { eCModEntry 1 }

eCModSubSlotIndex OBJECT-TYPE
	SYNTAX INTEGER
	ACCESS read-only
	STATUS mandatory
	DESCRIPTION
		"The subslot number of this module."
	::= { eCModEntry 2 }

eCModBootVersion OBJECT-TYPE
	SYNTAX DisplayString (SIZE(1..32))
	ACCESS read-only
	STATUS mandatory
	DESCRIPTION
		"The software boot eprom version of this module.  "
	::= { eCModEntry 3 }


--
-- IBM 8260 Ethernet 10BASE-FB 10-PORT Per-Port switchable Module
--
--
-- Port Table
--
e10PSFBPortTable OBJECT-TYPE
	SYNTAX SEQUENCE OF E10PSFBPortEntry
	ACCESS not-accessible
	STATUS mandatory
	DESCRIPTION
		"A table of port-specific information for each port of
		 this module type."
	::= { e10PSFB 2 }

e10PSFBPortEntry OBJECT-TYPE
	SYNTAX E10PSFBPortEntry
	ACCESS not-accessible
	STATUS mandatory
	DESCRIPTION
		"A list of port specific information about this
		 module's ports."
	INDEX { e10PSFBPortSlotIndex, e10PSFBPortIndex }
	::= { e10PSFBPortTable 1 }

E10PSFBPortEntry ::=
	SEQUENCE {
		e10PSFBPortSlotIndex
			INTEGER,
		e10PSFBPortIndex
			INTEGER,
		e10PSFBPortAdminState
			INTEGER,
		e10PSFBPortBuddySlot
			INTEGER,
		e10PSFBPortBuddyPort
			INTEGER,
		e10PSFBPortDipNetwork
			INTEGER,
		e10PSFBPortHipwr
			INTEGER
		}

e10PSFBPortSlotIndex OBJECT-TYPE
	SYNTAX INTEGER
	ACCESS read-only
	STATUS mandatory
	DESCRIPTION
		"The slot number of the module assocaited with this port."
	::= { e10PSFBPortEntry 1 }

e10PSFBPortIndex OBJECT-TYPE
	SYNTAX INTEGER
	ACCESS read-only
	STATUS mandatory
	DESCRIPTION
		"The port number with respect to the module it resides on."
	::= { e10PSFBPortEntry 2 }

e10PSFBPortAdminState OBJECT-TYPE
	SYNTAX INTEGER {
		enabled(1),
		disabled(2),
		redundant-primary(3),
		redundant-backup(4)
		}
	ACCESS read-write
	STATUS mandatory
	DESCRIPTION
		"The desired state of this port.  Setting this port to
		 redundant-primary or redundant-backup with invalid buddy
		 slot or buddy port will result in an error."
	::= { e10PSFBPortEntry 3 }

e10PSFBPortBuddySlot OBJECT-TYPE
	SYNTAX INTEGER
	ACCESS read-write
	STATUS mandatory
	DESCRIPTION
		"The slot index of the redundant port's buddy port."
	::= { e10PSFBPortEntry 4 }

e10PSFBPortBuddyPort  OBJECT-TYPE
	SYNTAX INTEGER
	ACCESS read-write
	STATUS mandatory
	DESCRIPTION
		"The port index of the redundant port's buddy. Valid ports
		 are those ports which are not redundant. The buddy port
		 admin state will be set to redundant."
	::= { e10PSFBPortEntry 5 }

e10PSFBPortDipNetwork OBJECT-TYPE
	SYNTAX INTEGER {
		ethernet-1(6),
		ethernet-2(7),
		ethernet-3(8),
		isolated-1(21),
		ethernet-4(32),
		ethernet-5(33),
		ethernet-6(34),
		ethernet-7(35),
		ethernet-8(36)
		}
	ACCESS read-only
	STATUS mandatory
	DESCRIPTION
		"The network indicated by the port's dip switches."
	::= { e10PSFBPortEntry 6 }

e10PSFBPortHipwr OBJECT-TYPE
	SYNTAX INTEGER {
		enable(1),
		disable(2)
		}
	ACCESS read-write
	STATUS mandatory
	DESCRIPTION
		"The current port high power optics mode. Setting
		 this variable to enable(1), will enable the port
		 to drive up to 4K meter fiber cable."
	::= { e10PSFBPortEntry 7 }

--
-- module specific table
--
e10PSFBModTable OBJECT-TYPE
	SYNTAX SEQUENCE OF E10PSFBModEntry
	ACCESS not-accessible
	STATUS mandatory
	DESCRIPTION
		"A list of module specific information about this module."
	::= { e10PSFB 6 }

e10PSFBModEntry OBJECT-TYPE
	SYNTAX E10PSFBModEntry
	ACCESS not-accessible
	STATUS mandatory
	DESCRIPTION
		"Values to describe module specific inormation."
	INDEX { e10PSFBModSlotIndex, e10PSFBModSubSlotIndex }
	::= { e10PSFBModTable 1 }

E10PSFBModEntry ::=
	SEQUENCE {
		e10PSFBModSlotIndex
			INTEGER,
		e10PSFBModSubSlotIndex
			INTEGER,
		e10PSFBModBootVersion
			DisplayString,
		e10PSFBModDipNVRam
			INTEGER
		}

e10PSFBModSlotIndex OBJECT-TYPE
	SYNTAX INTEGER
	ACCESS read-only
	STATUS mandatory
	DESCRIPTION
		"The slot index of this module."
	::= { e10PSFBModEntry 1 }

e10PSFBModSubSlotIndex OBJECT-TYPE
	SYNTAX INTEGER
	ACCESS read-only
	STATUS mandatory
	DESCRIPTION
		"The subslot index of this module. (e.g. mother boards
		 have subslot index equals to one."
	::= { e10PSFBModEntry 2 }

e10PSFBModBootVersion OBJECT-TYPE
	SYNTAX DisplayString (SIZE(1..32))
	ACCESS read-only
	STATUS mandatory
	DESCRIPTION
		"The software boot eprom version of this module.  "
	::= { e10PSFBModEntry 3 }

e10PSFBModDipNVRam OBJECT-TYPE
	SYNTAX INTEGER {
		enabled(1),
		disabled(2)
		}
	ACCESS read-only
	STATUS mandatory
	DESCRIPTION
		"The Non-Volatile RAM dip switch setting for this
		 module. Setting this object to enable(1) will cause
		 the module to be configured according to the
		 configuration which was saved in the non-volatile
		 storage."
	::= { e10PSFBModEntry 4 }


--
-- IBM 8260 Redundant Controller Module managed by Hub agent.
--

rCTL8000ModTable OBJECT-TYPE
	SYNTAX SEQUENCE OF RCTL8000ModEntry
	ACCESS not-accessible
	STATUS mandatory
	DESCRIPTION
		"A table that contains information about the Controller
		in the concentrator."
	::= { ocRCTL8000 1 }

rCTL8000ModEntry OBJECT-TYPE
	SYNTAX RCTL8000ModEntry
	ACCESS not-accessible
	STATUS mandatory
	DESCRIPTION
		"A list of information for the Controller module
		in the concentrator."
	INDEX { rCTL8000ModSlotIndex }
	::= { rCTL8000ModTable 1 }

RCTL8000ModEntry ::=
	SEQUENCE {
		rCTL8000ModSlotIndex
			INTEGER,
		rCTL8000ModOperState
			INTEGER,
		rCTL8000ModClockStatus
			INTEGER,
		rCTL8000ModTempStatus
			INTEGER
		}

rCTL8000ModSlotIndex OBJECT-TYPE
	SYNTAX INTEGER
	ACCESS read-only
	STATUS mandatory
	DESCRIPTION
		"The slot number for this module.  Note that this module will
		 always be in slot 17."
	::= { rCTL8000ModEntry 1 }

rCTL8000ModOperState OBJECT-TYPE
	SYNTAX INTEGER {
		active(1),
		standby(2)
		}
	ACCESS read-only
	STATUS mandatory
	DESCRIPTION
		"The operational state of the Controller module.  Specifically,
		this is an indicator of whether the Controller module is
		providing clock signals to the backplane.  An active Controller
		module provides clock signals to the backplane while a standby
		Controller module does not.  Note that only the active
		Controller is visible to an Hub agent; hence, this object
		will have the value active(1)."
	::= { rCTL8000ModEntry 2 }

rCTL8000ModClockStatus OBJECT-TYPE
	SYNTAX INTEGER {
		okay(1),
		faulty(2)
		}
	ACCESS read-only
	STATUS mandatory
	DESCRIPTION
		"The current status of the on-board clocks on this module."
	::= { rCTL8000ModEntry 3 }

rCTL8000ModTempStatus OBJECT-TYPE
	SYNTAX INTEGER {
		okay(1),
		extremeTemp(2)
		}
	ACCESS read-only
	STATUS mandatory
	DESCRIPTION
		"The overall temperature status for this concentrator as
		detected by this module.  This object's value is an aggregate
		of all temperature probes located within this concentrator as
		sensed by this module.  Hence, when at least one probe in
		the concentrator reports an extreme temperature, then this
		object will have the value extremeTemp(2)."
	::= { rCTL8000ModEntry 4 }

--
-- IBM 8260 Redundant Controller Module managed by IBM 8260 agent
--

ocRCTL8000ModTable OBJECT-TYPE
	SYNTAX SEQUENCE OF OcRCTL8000ModEntry
	ACCESS not-accessible
	STATUS mandatory
	DESCRIPTION
		"A table that contains information about the Controller
		in the concentrator."
	::= { ocRCTL8000 6 }

ocRCTL8000ModEntry OBJECT-TYPE
	SYNTAX OcRCTL8000ModEntry
	ACCESS not-accessible
	STATUS mandatory
	DESCRIPTION
		"A list of information for the Controller module
		in the concentrator."
	INDEX { ocRCTL8000ModSlotIndex, ocRCTL8000ModSubSlotIndex }
	::= { ocRCTL8000ModTable 1 }

OcRCTL8000ModEntry ::=
	SEQUENCE {
		ocRCTL8000ModSlotIndex
			INTEGER,
		ocRCTL8000ModSubSlotIndex
			INTEGER,
		ocRCTL8000ModBootVersion
			DisplayString,
		ocRCTL8000ModOperState
			INTEGER,
		ocRCTL8000ModClockStatus
			INTEGER,
		ocRCTL8000ModTempStatus
			INTEGER,
		ocRCTL8000ModAtoDConverterStatus
			INTEGER,
		ocRCTL8000ModPS1Status
			INTEGER,
		ocRCTL8000ModPS2Status
			INTEGER,
		ocRCTL8000ModPS3Status
			INTEGER,
		ocRCTL8000ModPS4Status
			INTEGER
		}

ocRCTL8000ModSlotIndex OBJECT-TYPE
	SYNTAX INTEGER
	ACCESS read-only
	STATUS mandatory
	DESCRIPTION
		"The slot number for this module."
	::= { ocRCTL8000ModEntry 1 }

ocRCTL8000ModSubSlotIndex OBJECT-TYPE
	SYNTAX INTEGER
	ACCESS read-only
	STATUS mandatory
	DESCRIPTION
		"The subslot number for this module."
	::= { ocRCTL8000ModEntry 2 }

ocRCTL8000ModBootVersion OBJECT-TYPE
	SYNTAX DisplayString (SIZE(1..32))
	ACCESS read-only
	STATUS mandatory
	DESCRIPTION
		"The software boot eprom version of this module.  "
	::= { ocRCTL8000ModEntry 3 }

ocRCTL8000ModOperState OBJECT-TYPE
	SYNTAX INTEGER {
		active(1),
		standby(2)
		}
	ACCESS read-only
	STATUS mandatory
	DESCRIPTION
		"The operational state of the Controller module.
		Specifically, this is an indicator of whether the Controller
		module is providing clock signals to the backplane.  An
		active Controller module provides clock signals to the
		backplane while a standby Controller module does not."
	::= { ocRCTL8000ModEntry 4 }

ocRCTL8000ModClockStatus OBJECT-TYPE
	SYNTAX INTEGER {
		okay(1),
		faulty(2)
		}
	ACCESS read-only
	STATUS mandatory
	DESCRIPTION
		"The current status of the on-board clocks on this module."
	::= { ocRCTL8000ModEntry 5 }

ocRCTL8000ModTempStatus OBJECT-TYPE
	SYNTAX INTEGER {
		okay(1),
		extremeTemp(2)
		}
	ACCESS read-only
	STATUS mandatory
	DESCRIPTION
		"The overall temperature status for the concentrator as
		detected by this module.  This object's value is an aggregate
		of all the temperature probes located within this
		concentrator as sensed by this module.  Hence, when at least
		one probe in the concentrator reports an extreme temperature,
		then this object will have the value extremeTemp(2)."
	::= { ocRCTL8000ModEntry 6 }

ocRCTL8000ModAtoDConverterStatus OBJECT-TYPE
	SYNTAX INTEGER {
		okay(1),
		faulty(2)
		}
	ACCESS read-only
	STATUS mandatory
	DESCRIPTION
		"The current status of the on-board A/D converter.
		Typically, when this object has a value of faulty(2), it
		is because the value obtained from the A/D converter internal
		test channel is out of tolerance from what is specified by
		the manufacturer."
	::= { ocRCTL8000ModEntry 7 }

ocRCTL8000ModPS1Status OBJECT-TYPE
	SYNTAX INTEGER {
		active(1),
		faulty(3),
		not-installed(4)
		}
	ACCESS read-only
	STATUS mandatory
	DESCRIPTION
		"The current status of powersupply 1."
	::= { ocRCTL8000ModEntry 8 }

ocRCTL8000ModPS2Status OBJECT-TYPE
	SYNTAX INTEGER {
		active(1),
		faulty(3),
		not-installed(4)
		}
	ACCESS read-only
	STATUS mandatory
	DESCRIPTION
		"The current status of powersupply 2."
	::= { ocRCTL8000ModEntry 9 }

ocRCTL8000ModPS3Status OBJECT-TYPE
	SYNTAX INTEGER {
		active(1),
		faulty(3),
		not-installed(4)
		}
	ACCESS read-only
	STATUS mandatory
	DESCRIPTION
		"The current status of powersupply 3."
	::= { ocRCTL8000ModEntry 10 }

ocRCTL8000ModPS4Status OBJECT-TYPE
	SYNTAX INTEGER {
		active(1),
		faulty(3),
		not-installed(4)
		}
	ACCESS read-only
	STATUS mandatory
	DESCRIPTION
		"The current status of powersupply 4."
	::= { ocRCTL8000ModEntry 11 }


--
-- IBM 8260 Ethernet Network Monitor Card
--

eMACModTable OBJECT-TYPE
	SYNTAX SEQUENCE OF EMACModEntry
	ACCESS not-accessible
	STATUS mandatory
	DESCRIPTION
		"A table that contains information about Ethernet
		Network Monitor Cards in the IBM 8260 Hub.  "
	::= { eMAC 6 }

eMACModEntry OBJECT-TYPE
	SYNTAX EMACModEntry
	ACCESS not-accessible
	STATUS mandatory
	DESCRIPTION
		"A list of information for an Ethernet Network Monitor
		 Card in the IBM 8260 Hub."
	INDEX { eMACModSlotIndex, eMACModSubSlotIndex}
	::= { eMACModTable 1 }

EMACModEntry ::=
	SEQUENCE {
		eMACModSlotIndex
			INTEGER,
		eMACModSubSlotIndex
			INTEGER,
		eMACModBootVersion
			DisplayString,
		eMACModIpAddress
			IpAddress,
		eMACModSubnetMask
			IpAddress,
		eMACModDefaultGateway
			IpAddress,
		eMACModStationAddr
			OCTET STRING,
		eMACModInterfaceMode
			INTEGER,
		eMACModRMONHostStatsMode
			INTEGER

	}


eMACModSlotIndex OBJECT-TYPE
	SYNTAX INTEGER
	ACCESS read-only
	STATUS mandatory
	DESCRIPTION
		"The slot number of this card."
	::= { eMACModEntry 1 }

eMACModSubSlotIndex OBJECT-TYPE
	SYNTAX INTEGER
	ACCESS read-only
	STATUS mandatory
	DESCRIPTION
		"The subslot number of this card."
	::= { eMACModEntry 2 }

eMACModBootVersion OBJECT-TYPE
	SYNTAX DisplayString (SIZE(1..32))
	ACCESS read-only
	STATUS mandatory
	DESCRIPTION
		"The software boot eprom version of this module.  "
	::= { eMACModEntry 3 }

eMACModIpAddress OBJECT-TYPE
	SYNTAX IpAddress
	ACCESS read-only
	STATUS mandatory
	DESCRIPTION
		"The current IP address of this card and the associated interface."
	::= { eMACModEntry 4 }


eMACModSubnetMask OBJECT-TYPE
	SYNTAX IpAddress
	ACCESS read-only
	STATUS mandatory
	DESCRIPTION
		"The current subnet mask of this card and the associated interface."
	::= { eMACModEntry 5 }


eMACModDefaultGateway OBJECT-TYPE
	SYNTAX IpAddress
	ACCESS read-only
	STATUS mandatory
	DESCRIPTION
		"The current default gateway of this card and the associated interface.
		 Note that a value of 0.0.0.0 indicates that this interface is not con-
		 configured to be used with a default gateway."
	::= { eMACModEntry 6 }

eMACModStationAddr OBJECT-TYPE
	SYNTAX OCTET STRING (SIZE(6))
	ACCESS read-only
	STATUS mandatory
	DESCRIPTION
		"A 6 octet address that uniquely identifies this card.
		Note that an address of 00-00-00-00-00-00 is invalid
		and the module has failed."
	::= { eMACModEntry 7 }

eMACModInterfaceMode OBJECT-TYPE
	SYNTAX INTEGER {
		enabled(1),
		disabled(2),
		standby(3)
		}
	ACCESS read-write
	STATUS mandatory
	DESCRIPTION
		"The desired connectvity mode of this card.  When this
		 attribute is set to enabled and the card is set to a
		 network, it will forward  messages to and from the master
		 Distributed Management Module.  If this attribute is set
		 to disabled, the card may still collect statistics but not
		 forward messages to and from the Distributed Management Module."
	::= { eMACModEntry 8 }

eMACModRMONHostStatsMode  OBJECT-TYPE
       SYNTAX INTEGER {
	       enabled(1),
	       disabled(2)
	       }
	ACCESS read-write
	STATUS mandatory
	DESCRIPTION
		"The desired RMON host staticstics mode of this card.
		 When this attribute is set to enabled, the card will
		 gather RMON host table statistics.  Note that when this
		 attribute is enabled, the accuracy of all statistics
		 may be impaired during peak loads."
	::= { eMACModEntry 9 }


--
-- IBM 8260 Distribute Management Module
--

xDMMModTable OBJECT-TYPE
	SYNTAX SEQUENCE OF XDMMModEntry
	ACCESS not-accessible
	STATUS mandatory
	DESCRIPTION
		"A table that contains module information about each
		DMM module in the concentrator."
	::= { xDMM 6 }

xDMMModEntry OBJECT-TYPE
	SYNTAX XDMMModEntry
	ACCESS not-accessible
	STATUS mandatory
	DESCRIPTION
		"A list of module information for each DMM module
		in the concentrator."
	INDEX { xDMMModSlotIndex, xDMMModSubSlotIndex }
	::= { xDMMModTable 1 }

XDMMModEntry ::=
	SEQUENCE {
		xDMMModSlotIndex
			INTEGER,
		xDMMModSubSlotIndex
			INTEGER,
		xDMMModBootVersion
			DisplayString,
		xDMMModMasterPriority
			INTEGER,
		xDMMModMasterStatus
			INTEGER,
		xDMMModHubSerial
			DisplayString
	}

xDMMModSlotIndex OBJECT-TYPE
	SYNTAX INTEGER
	ACCESS read-only
	STATUS mandatory
	DESCRIPTION
		"The slot number of this module."
	::= { xDMMModEntry 1 }

xDMMModSubSlotIndex OBJECT-TYPE
	SYNTAX INTEGER
	ACCESS read-only
	STATUS mandatory
	DESCRIPTION
		"The subslot number of this module."
	::= { xDMMModEntry 2 }

xDMMModBootVersion OBJECT-TYPE
	SYNTAX DisplayString (SIZE(1..32))
	ACCESS read-only
	STATUS mandatory
	DESCRIPTION
		"The software boot eprom version of this module.  "
	::= { xDMMModEntry 3 }

xDMMModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent.  Ten is the
		highest and one is the lowest.  Priority is
		only used when an election occurs.  Mastership is not
		preemptive unless the reset mastership command is used."
	::= { xDMMModEntry 4 }

xDMMModMasterStatus OBJECT-TYPE
	SYNTAX INTEGER {
		master(1),
		non-master(2),
		electing(3)
		}
	ACCESS read-only
	STATUS mandatory
	DESCRIPTION
		"The mastership status of this agent."
	::= { xDMMModEntry 5 }

xDMMModHubSerial OBJECT-TYPE
	SYNTAX DisplayString
	ACCESS read-only
	STATUS mandatory
	DESCRIPTION
		"The Hub serial number mastership is presiding over.
		 Zero length string for slaves."
	::= { xDMMModEntry 6 }


--
-- Token Ring Establishment Controller Module
--

tnnMSECModTable OBJECT-TYPE
	SYNTAX SEQUENCE OF TnnMSECModEntry
	ACCESS not-accessible
	STATUS mandatory
	DESCRIPTION
		"A list of module-specific information associated
		with a particular tnnMS-EC module in the concentrator."
	::= { tnnMSEC 1 }

tnnMSECModEntry OBJECT-TYPE
	SYNTAX TnnMSECModEntry
	ACCESS not-accessible
	STATUS mandatory
	DESCRIPTION
		"A description of the tnnMS-EC module attributes."
	INDEX { tnnMSECModSlotIndex }
	::= { tnnMSECModTable 1 }

TnnMSECModEntry ::=
	SEQUENCE {
		tnnMSECModSlotIndex
			INTEGER,
		tnnMSECModSoftwareVersion
			DisplayString,
		tnnMSECModSystemStatusCode
			DisplayString,
		tnnMSECModRingSpeed
			INTEGER,
		tnnMSECModNetworkStatus
			INTEGER,
		tnnMSECModIpAddress
			IpAddress,
		tnnMSECModMACStationAddr
			OCTET STRING
	}

tnnMSECModSlotIndex OBJECT-TYPE
	SYNTAX INTEGER
	ACCESS read-only
	STATUS mandatory
	DESCRIPTION
		"The slot number of this module."
	::= { tnnMSECModEntry 1 }


tnnMSECModSoftwareVersion OBJECT-TYPE
       SYNTAX DisplayString (SIZE(1..10))
       ACCESS read-only
       STATUS mandatory
       DESCRIPTION
	       "The version number of the software."
       ::= { tnnMSECModEntry 2 }

tnnMSECModSystemStatusCode OBJECT-TYPE
	SYNTAX DisplayString (SIZE(43))
	ACCESS read-only
	STATUS mandatory
	DESCRIPTION
		"A 43 octet indication of the current applicable
		IBM 3174 System Status Code. For more information
		consult the tnnMS-EC reference manual."
	::= { tnnMSECModEntry 3 }

tnnMSECModRingSpeed OBJECT-TYPE
	SYNTAX INTEGER {
	     fourMegabit(1),
	     sixteenMegabit(2)
	     }
	ACCESS read-write
	STATUS mandatory
	DESCRIPTION
		"The ring's bandwidth in Mega-bits per second."
	::= { tnnMSECModEntry 4 }

tnnMSECModNetworkStatus OBJECT-TYPE
	SYNTAX INTEGER {
	     okay(1),
	     closed(2),
	     beaconing(3)
	     }
	ACCESS read-only
	STATUS mandatory
	DESCRIPTION
		"The status of the ring containing this module."
	::= {tnnMSECModEntry 5}

tnnMSECModIpAddress OBJECT-TYPE
       SYNTAX IpAddress
       ACCESS read-only
       STATUS mandatory
       DESCRIPTION
	       "The IP Address of this module."
       ::= { tnnMSECModEntry 6 }

tnnMSECModMACStationAddr OBJECT-TYPE
	SYNTAX OCTET STRING
	ACCESS read-only
	STATUS mandatory
	DESCRIPTION
		"A 6 octet address that uniquely identifies the MAC
		address of this module."
	::= { tnnMSECModEntry 7 }

tnnMSECPortTable OBJECT-TYPE
	SYNTAX SEQUENCE OF TnnMSECPortEntry
	ACCESS not-accessible
	STATUS mandatory
	DESCRIPTION
		"A table of port-specific information for each port of
		this module type."
	::= { tnnMSEC 2 }

tnnMSECPortEntry OBJECT-TYPE
	SYNTAX TnnMSECPortEntry
	ACCESS not-accessible
	STATUS mandatory
	DESCRIPTION
		"A description of this module's port attributes."
	INDEX { tnnMSECPortSlotIndex, tnnMSECPortIndex }
	::= { tnnMSECPortTable 1 }

TnnMSECPortEntry ::=
	SEQUENCE {
		tnnMSECPortSlotIndex
			INTEGER,
		tnnMSECPortIndex
			INTEGER
	}

tnnMSECPortSlotIndex OBJECT-TYPE
	SYNTAX INTEGER
	ACCESS read-only
	STATUS mandatory
	DESCRIPTION
		"The slot number of this port's module."
	::= { tnnMSECPortEntry 1 }


tnnMSECPortIndex OBJECT-TYPE
	SYNTAX INTEGER
	ACCESS read-only
	STATUS mandatory
	DESCRIPTION
		"The port number of this port."
	::= { tnnMSECPortEntry 2 }

tnnMSECTrunkTable OBJECT-TYPE
	SYNTAX SEQUENCE OF TnnMSECTrunkEntry
	ACCESS not-accessible
	STATUS mandatory
	DESCRIPTION
		"A list of trunk-specific information about each trunk
		for this module type."
	::= { tnnMSEC 3 }

tnnMSECTrunkEntry OBJECT-TYPE
	SYNTAX TnnMSECTrunkEntry
	ACCESS not-accessible
	STATUS mandatory
	DESCRIPTION
		"A description of tnnMS-EC trunk attributes."
	INDEX { tnnMSECTrunkSlotIndex, tnnMSECTrunkIndex }
	::= { tnnMSECTrunkTable 1 }

TnnMSECTrunkEntry ::=
	SEQUENCE {
		tnnMSECTrunkSlotIndex
			INTEGER,
		tnnMSECTrunkIndex
			INTEGER
	}

tnnMSECTrunkSlotIndex OBJECT-TYPE
	SYNTAX INTEGER
	ACCESS read-only
	STATUS mandatory
	DESCRIPTION
		"A unique value that identifies a particular module.  Its
		value ranges between 1 and modSlotNumber.  The module
		identified by a particular value of this index is the same
		module as indentified by the same value of
		trunkSlotIndex."
	::= { tnnMSECTrunkEntry 1 }


tnnMSECTrunkIndex OBJECT-TYPE
	SYNTAX INTEGER
	ACCESS read-only
	STATUS mandatory
	DESCRIPTION
		"The trunk number for this trunk."
	::= { tnnMSECTrunkEntry 2 }







--
-- modSummary
--
-- This group was designed to enhance the performance of retrievals of
-- module related information.  It is specifically targeted for use by
-- closely designed management applications.  It is NOT designed for use
-- by off the shelf applications and is documented here only for completeness.
--
-- The summary group encodes the module information into an octet string
-- that includes the values of each object in the module, port and trunk
-- tables.  This allows fast retrieval of a large amount of information
-- within no more that 17 Get operations, rather than utilizing 17 operations
-- (max) for the modules, and 17 x Number of Ports (max) for the port
-- information, and 17 x Number of Trunks (max) for the trunk information.
--
-- Users should be aware that this table requires the application to
-- parse out information and therefore, applications should be sensitive to
-- the positioning of information within the summary string.
--


modSummaryTable OBJECT-TYPE
	SYNTAX SEQUENCE OF ModSummaryEntry
	ACCESS not-accessible
	STATUS mandatory
	DESCRIPTION
		"A table of condensed module information."
	::= { modules 5 }

modSummaryEntry OBJECT-TYPE
	SYNTAX ModSummaryEntry
	ACCESS not-accessible
	STATUS mandatory
	DESCRIPTION
		"A summary of all the generic and value added information
		associated with this module."
	INDEX { modSummarySlotIndex }
	::= { modSummaryTable 1 }

ModSummaryEntry ::=
	SEQUENCE {
		modSummarySlotIndex
			INTEGER,
		modSummaryInfo
			OCTET STRING
		}

modSummarySlotIndex OBJECT-TYPE
	SYNTAX INTEGER
	ACCESS read-only
	STATUS mandatory
	DESCRIPTION
		"The slot number of this module that this summary
		pertains to."
	::= { modSummaryEntry 1 }

modSummaryInfo OBJECT-TYPE
	SYNTAX OCTET STRING (SIZE(0..512))
	ACCESS read-only
	STATUS mandatory
	DESCRIPTION
		"A summary of all information relating to this module in
		condensed format.  The condensed format is only as large
		as needed to hence the largest value which usually is one
		octet.  The TCP port for the terminal server, however,
		uses 4 octets.

		The summary consists of a header, a module portion, a port
		portion, and a trunk portion.  Each portion consists of
		generic information and module specific information.
		For example, the module information consists of the
		modTable entry for this slot and the specMods module
		table information for this module type for this slot.


		---------------------------------------------------
		The header consists of the following octets:
			Version of structure : 1

			Number of octets in generic module
			Number of octets in specific module
			Number of octets in generic port
			Number of octets in specific port
			Number of octets in generic trunk
			Number of octets in specific trunk

		The format of the data portion is as follows:

			Some of the modTable:
				modType
				modClass
				modDescr
				modVersion
				modNetwork
				modNetworkType
				modStatus

				modNumPorts
				modNumTrunks

			specMods module table (for this module)
				Not including slot number.

		For each port:
			Some of the portTable:
				portType
				portConnector
				portStatus
				portAdminState
				portNetwork
				portNetworkType

			specMods port table (for this port's module)
				Not including slot and port number.

		For each trunk:
			Some of the trunkTable:
				trunkType
				trunkConnector
				trunkStatus
				trunkAdminState
				trunkWrapState
				trunkNeighbor


			specMods trunk table (for this trunk's module)
				Not including slot and trunk number.

		---------------------------------------------------
		Version 2 of the summary structure:

		Version 2 is returned only when there is a possibility
		of multiple modules per slot.  This is a function of
		the platform (concentrator).  The IBM 8260 platform
		is an example of this.  Hub modules in the IBM 8260
		platform will still be represented by version 1 structure.

		Version 2 is an array of version 1 structures,

		Version: 2

		Maximum number of v1 structures = 8.
		Number of v1 structures to follow => max of 8.
		Reserved octet = 0.

		2 octets each describing the length of v1 summaries:
			Number of octets in summary #1.
			Number of octets in summary #2.
			Number of octets in summary #3.
			Number of octets in summary #4.
			Number of octets in summary #5.
			Number of octets in summary #6.
			Number of octets in summary #7.
			Number of octets in summary #8.

		Array of Version 1 structures.

		For example, there are 3 modules in slot 5, in subslot
		locations 1, 3 and 8.

			Byte		Description
			----		-----------
			 1		Version = 2
			 2		Max number of v1 structures (8)
			 3		Number of v1 structures (3)
			 4		Reserved (0)
			 5&6		Number of bytes N(1)
			 7&8		Number of bytes N(2) = 0
			 9&10		Number of bytes N(3)
			11&12		Number of bytes N(4) = 0
			13&14		Number of bytes N(4) = 0
			15&16		Number of bytes N(4) = 0
			17&18		Number of bytes N(4) = 0
			19&20		Number of bytes N(4)

			21
			to		Version 1 summary for module in sslot 1
			21 + N(1)

			21 + N(1)
			to		Version 1 summary for module in sslot 3
			(21 + N(1)) + N(3)

			(21 + N(1)) + N(3)
			to		Version 1 summary for module in sslot 8

			((21 + N(1)) + N(3)) + N(8)

			21 to 21 + N(1) Version 1 summary for module in sslot 1

		----------------------------------------------------

		In all of the above, the index for all of these tables
		is condensed out of the summary. "
	::= { modSummaryEntry 2 }


--
--
-- The IBM 8260 Modules Table
--
--
-- This table represents the information about modules
-- including mother boards and daughter boards.
--
-- Modules are instantiated by slot and subslot.  The slot
-- is the physical location of the module in the concentrator.
-- The subslot indicates the position of the module within a slot.
--
-- For example, the mother board is always subslot 1 of a slot, indicating
-- that it is the first module in that slot.  The first daughter board
-- would of course be the second module in that slot, and hence, subslot 2.
--


ocModTable OBJECT-TYPE
	SYNTAX SEQUENCE OF OcModEntry
	ACCESS not-accessible
	STATUS mandatory
	DESCRIPTION
		"A table that contains generic information about every
		module that is present within the concentrator."
	::= { modules 6 }

ocModEntry OBJECT-TYPE
	SYNTAX OcModEntry
	ACCESS not-accessible
	STATUS mandatory
	DESCRIPTION
		"A list of information for each module in the concentrator."
	INDEX { ocModSlotIndex, ocModSubSlotIndex }
	::= { ocModTable 1 }

OcModEntry ::=
	SEQUENCE {
		ocModSlotIndex
			INTEGER,
		ocModSubSlotIndex
			INTEGER,
		ocModType
			INTEGER,
		ocModClass
			INTEGER,
		ocModDescr
			DisplayString,
		ocModVersion
			DisplayString,
		ocModVendor
			INTEGER,
		ocModResetModule
			INTEGER,
		ocModConfigToDips
			INTEGER,
		ocModConfigured
			INTEGER,
		ocModNetwork
			INTEGER,
		ocModNetworkType
			INTEGER,
		ocModStatus
			INTEGER,
		ocModNumPorts
			INTEGER,
		ocModNumTrunks
			INTEGER,
		ocModNumSubSlots
			INTEGER

		}


ocModSlotIndex OBJECT-TYPE
	SYNTAX INTEGER
	ACCESS read-only
	STATUS mandatory
	DESCRIPTION
		"The unique slot number of this module.  Its value ranges
		between 1 and concNumSlots and remains constant at
		least from one re-initialization of the entity's network
		management system to the next re-initialization."
	::= { ocModEntry 1 }

ocModSubSlotIndex OBJECT-TYPE
	SYNTAX INTEGER
	ACCESS read-only
	STATUS mandatory
	DESCRIPTION
		"The unique subslot number of this module.  Its value ranges
		between 1 and the value of ocModNumSubSlots for the
		mother board in this slot (ocModNumSubSlots.<slot>.1),
		and it remains constant between re-initializations of the
		mother board.

		The mother board is ALWAYS the first subslot index in any
		particular slot.  Not all subslots must be occupied, and an
		empty subslot will not return an instance."
	::= { ocModEntry 2 }

ocModType OBJECT-TYPE
	SYNTAX INTEGER {
		module-unmanageable(1), -- not manageable
		module-unknown(2),	-- only generically manageable
		module-cnnNS-CTL(3),	-- Controller
		module-ennMS-MGT(4),	-- Ethernet Management
		module-ennMS-FIB(5),	-- Ethernet Fiber
		module-ennMS-UTP(6),	-- Ethernet 10BASE-T
		module-ennMS-RJ45S(7),  -- Ethernet 10BASE-T
		module-ennMS-BNC(8),	-- Ethernet BNC
		module-eennPS-BRG(9),	-- EBM
		module-esnnPS-RTR(10),  -- Cisco Serial
		module-eennPS-RTR(11),  -- Cisco Ethernet
		module-ennPS-AUIF(12),  -- Ethernet AUI Female
		module-ennPS-AUIM(13),  -- Ethernet AUI Male
		module-t08MS-RJ45S(14), -- Token Ring 8-port MAU module
		module-ennPS-FIB(15),	-- Ethernet Fiber port switching
		module-ennPS-FBP(16),	-- Ethernet 10BASE-F port switching
		module-ennMS-TELCO(17), -- Ethernet 10BASE-T
		module-ennPS-TELCO(18),  -- Ethernet 10BASE-T port switching
		module-tnnMS-RJ45S(19),    -- Token Ring Media Module
		module-tnnMS-FIB(20),	-- Token Ring FiberOptic Repeater
		module-ennMS-TS(21),	-- Ethernet Terminal Server
		module-ennMS-FOIRL(22), -- Ethernet FOIRL
		module-cnnNS-RCTL(23),  -- Redundant Controller
		module-ennPS-FB(24),	-- Ethernet 10BASE-F
		module-fnnMS-MGT(25),	-- FDDI managment module (FMM)
		module-fnnMS-FBMIC(26), -- FDDI media w/ fiber ANSI MIC conn.
		module-fnnMS-ST(27), -- FDDI media w/ fiber ST conn.
		module-fnnMS-DB9(28),	-- FDDI w/ shielded copper DB9 conn.
		module-ennCS-TELCO(29),		-- Ethernet 10BASE-T per-connector
		module-tnnPS-BRG(30),	-- Token Ring Bridge
		module-ee06PS-BRG(31),  -- Ethernet Interconnect Module
		module-tnnMS-MGT(32),	-- Token Ring Management
		module-cnnNS-HCTL(33),  -- Hidden Controller
		module-EC(35),  -- Ethernet Carrier Module

		module-DMM(43),   -- Distributed Management Module

		module-E-MAC(45),	-- Ethernet MAC monitor card
		module-E10PS-FB(46),	-- Ethernet 10-port per-port switchable fiber
		module-E24PS-6(47),	-- Ethernet 24-port per-port switching
		module-ennMS-TELCOS(48),  -- Ethernet 10BASE-T Security Module
		module-RCTL-8000(50),	-- IBM 8260 Ctlr (managed by IBM 8260 mgmt)

		module-CNNNS-RCLS(51),  -- Load Sharing Redundant Controller



		module-tnnMS-EC(62)	-- 3174 Establistment Controller

		,
		module-tnnMS-TDDI(65)	-- FDDI w/ copper RJ45 conn.




		}
	ACCESS read-only
	STATUS mandatory
	DESCRIPTION
		"The unique type identifier for this module.  This type
		is used to identify the branch in specMods (see below).

		module-unmanageable(1) means that only the following
		objects are valid for this module:

			ocModSlotIndex
			ocModClass
			ocModVersion
			ocModVendor
			ocModReset
			ocModConfigToDips
			ocModConfigured

		module-unknown(2) means that all the generic attributes
		are manageable, but there is no specMods branch
		for this module as viewed by this agent."
		::= { ocModEntry 3 }

ocModClass OBJECT-TYPE
	SYNTAX INTEGER {

		controller(1),
		mgmt(2),
		ethernet-media(3),
		ethernet-interconnect(4),
		ethernet-portswitching-media(5),
		token-ring-media(6),
		terminal-server(7),
		fddi-media(8),
		token-ring-mgmt(9),
		ethernet-connswitching-media(10),
		token-ring-interconnect(11),
		fddi-mgmt(12),
		hub8260-token-ring-media(13),
		ethernet-carrier(14),
		hub8260-oem-specials(15),

		network-monitor(16),

		hub8260-download(17),

		ethernet-media-extended(19),
		token-ring-mod-interconnect(20)


		}
	ACCESS read-only
	STATUS mandatory
	DESCRIPTION
		"The class of this module.  The class defines the
	internal data structure used to manage this module."
	::= { ocModEntry 4 }

ocModDescr OBJECT-TYPE
	SYNTAX DisplayString (SIZE(1..128))
	ACCESS read-only
	STATUS mandatory
	DESCRIPTION
		"A textual string containing information about the module."
	::= { ocModEntry 5 }

ocModVersion OBJECT-TYPE
	SYNTAX DisplayString (SIZE(1..32))
	ACCESS read-only
	STATUS mandatory
	DESCRIPTION
		"The software version number of this module.  "
	::= { ocModEntry 6 }

ocModVendor OBJECT-TYPE
	SYNTAX INTEGER {
		chipcom(1),
		cisco(2),
		pilkington(3),
		datability(5),
		ibm(6),
		raycom(7),
		retix(8),
		intellicom(9)
		}
	ACCESS read-only
	STATUS mandatory
	DESCRIPTION
		"The vendor of this module."
	::= { ocModEntry 7 }

ocModResetModule OBJECT-TYPE
	SYNTAX INTEGER {
		noReset(1),
		reset(2)
		}
	ACCESS read-write
	STATUS mandatory
	DESCRIPTION
		"Setting this object to reset(2) causes this module to
		reset."
	::= { ocModEntry 8 }

ocModConfigToDips OBJECT-TYPE
	SYNTAX INTEGER {
		noConfigure(1),
		configure(2)
		}
	ACCESS read-write
	STATUS mandatory
	DESCRIPTION
		"Setting this object to configure(2) causes this module to
		configure based on the dip switch settings.  Note, if the
		NV dip switch (if applicable) is set to configure from NV,
		then the module will retrieve its configuration from the
		on-board non-volatile storage."
	::= { ocModEntry 9 }

ocModConfigured OBJECT-TYPE
	SYNTAX INTEGER {
		notConfigured(1),
		configured(2)
		}
	ACCESS read-only
	STATUS mandatory
	DESCRIPTION
		"This object indicates whether this module has already been
		configured.  An unconfigured module is configured to a safe
		state (ports are disabled and the module is isolated from
		the backplane networks)."
	::= { ocModEntry 10 }


ocModNetwork OBJECT-TYPE
	SYNTAX INTEGER {
		other(1),
		isolated(2),
		port-switching(3),
		front-panel(5),
		ethernet-1(6),
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22),		-- isolated networks within the
		isolated-3(23),		-- module - multiple isolated networks.
		isolated-4(24),
		isolated-5(25),
		isolated-6(26),
		isolated-7(27),
		isolated-8(28),
		isolated-9(29),
		isolated-10(30),
		isolated-11(31),
		ethernet-4(32),
		ethernet-5(33),
		ethernet-6(34),
		ethernet-7(35),
		ethernet-8(36)

		}
	ACCESS read-write
	STATUS mandatory
	DESCRIPTION
		"The network that this module is attached to.

		Setting this module to a value that it does not support
		will return an invalidData error."
	::= { ocModEntry 11 }

ocModNetworkType OBJECT-TYPE
	SYNTAX INTEGER {
		other(1),	    -- other only
		port-switching(3),  -- use portNetwork
		ethernet(5),	    -- ethernet 1-3 or 1-8, isolated
		token-ring(6), -- token-ring 1-7, isolated,

		fddi(7),	    -- fddi 1-4, isolated
		serial(8)	    -- front or isolated only
		}
	ACCESS read-only
	STATUS mandatory
	DESCRIPTION
		"The network type of this module. The network type
		reflects the valid values for ocModNetwork."
	::= { ocModEntry 12 }

ocModStatus OBJECT-TYPE
	SYNTAX INTEGER {
		okay(1),
		fatalError(10),
		booting(20),
		partial-failure(21),
		notInserted(30),
		speedMismatch(31)
		}
	ACCESS read-only
	STATUS mandatory
	DESCRIPTION
		"The module's status."
	::= { ocModEntry 13 }

ocModNumPorts OBJECT-TYPE
	SYNTAX INTEGER
	ACCESS read-only
	STATUS mandatory
	DESCRIPTION
		"The number of ports on this module.  Note, ports may be
		physical ports like 10BASE-T ports, or logical, like
		the bridge module ports."
	::= { ocModEntry 14 }

ocModNumTrunks OBJECT-TYPE
	SYNTAX INTEGER
	ACCESS read-only
	STATUS mandatory
	DESCRIPTION
		"The number of trunks on this module.  Note, trunks
		are links that are, by definition, backbone connections.
		Examples of trunks are ring in and ring out ports for
		token ring, and the connections for rings to the backplane."
	::= { ocModEntry 15 }

ocModNumSubSlots OBJECT-TYPE
	SYNTAX  INTEGER
	ACCESS  read-only
	STATUS  mandatory
	DESCRIPTION
		"The number of possible submodules that can exist in this
		slot."
	::= { ocModEntry 16 }


-- The groups group

-- These objects define ports which have been assigned to groups and actions
-- which can be performed on the groups.  To add ports to a group,
-- groupSetAction should be set to add-ports(1) and the port(s) defined
-- by groupSetSlotIndex and groupSetPortIndex will be added to the group
-- groupSetGroupID, if the port exists and is not a logical port.  To remove
-- ports from a group, groupSetAction should be set to delete-ports(2) and
-- the port(s) defined by groupSetSlotIndex and groupSetPortIndex will be
-- removed from the group groupSetGroupID.   To change the admin state of
-- all ports in the group, groupSetAction should be set to
-- set-admin-state(3) and the ports in group groupSetGroupID will be set
-- to the state defined in groupSetAdminState.

groupPortTable OBJECT-TYPE
	SYNTAX SEQUENCE OF GroupPortEntry
	ACCESS not-accessible
	STATUS mandatory
	DESCRIPTION
		"A list of groups that each port is in. Each port can
		can be in 0, 1, or many groups."
	::= { groups 1 }

groupPortEntry OBJECT-TYPE
	SYNTAX GroupPortEntry
	ACCESS not-accessible
	STATUS mandatory
	DESCRIPTION
		"The groups corresponding to a particular port."
	INDEX { groupPortSlotIndex, groupPortIndex }
	::= { groupPortTable 1 }

GroupPortEntry ::=
	SEQUENCE {
		groupPortSlotIndex
			INTEGER,
		groupPortIndex
			INTEGER,
		groupPortGroupID
			OCTET STRING
		}

groupPortSlotIndex OBJECT-TYPE
	SYNTAX INTEGER
	ACCESS read-only
	STATUS mandatory
	DESCRIPTION
		"The slot number that contains this port."
	::= { groupPortEntry 1 }

groupPortIndex OBJECT-TYPE
	SYNTAX INTEGER
	ACCESS read-only
	STATUS mandatory
	DESCRIPTION
		"The port number within this slot. Logical ports
		can not be put into groups."
	::= { groupPortEntry 2 }

groupPortGroupID OBJECT-TYPE
	SYNTAX OCTET STRING (SIZE(0..8))
	ACCESS read-only
	STATUS mandatory
	DESCRIPTION
		"The group(s) to which the port has been assigned."
	::= { groupPortEntry 3 }


groupSummaryTable OBJECT-TYPE
	SYNTAX SEQUENCE OF GroupSummaryEntry
	ACCESS not-accessible
	STATUS mandatory
	DESCRIPTION
		"A table of condensed group information listing all the ports
		in each group."
	::= { groups 2 }

groupSummaryEntry OBJECT-TYPE
	SYNTAX GroupSummaryEntry
	ACCESS not-accessible
	STATUS mandatory
	DESCRIPTION
		"The summary of all the ports in a particular group."
	INDEX { groupSummaryGroupID, groupSummaryIndex }
	::= { groupSummaryTable 1 }

GroupSummaryEntry ::=
	SEQUENCE {
		groupSummaryGroupID
			INTEGER,
		groupSummaryIndex
			INTEGER,
		groupSummaryPorts
			OCTET STRING
		}

groupSummaryGroupID OBJECT-TYPE
	SYNTAX INTEGER {
		group-1(1),
		group-2(2),
		group-3(3),
		group-4(4),
		group-5(5),
		group-6(6),
		group-7(7),
		group-8(8)
		}
	ACCESS read-only
	STATUS mandatory
	DESCRIPTION
		"The group to which the ports have been assigned. A port
		can be in one or more groups."
	::= { groupSummaryEntry 1 }

groupSummaryIndex OBJECT-TYPE
	SYNTAX INTEGER
	ACCESS read-only
	STATUS mandatory
	DESCRIPTION
		"The index into the summary array. Up to 256 ports will be shown
		in groupSummaryPorts for each value in this entry."
	::= { groupSummaryEntry 2 }

groupSummaryPorts OBJECT-TYPE
	SYNTAX OCTET STRING (SIZE(0..1400))
	ACCESS read-only
	STATUS mandatory
	DESCRIPTION
		"A condensed list of all the ports in this group. The summary
		is in the format: Slotx PortX SlotY PortY ..."
	::= { groupSummaryEntry 3 }


groupSet	OBJECT IDENTIFIER ::= { groups 3 }


groupSetAction OBJECT-TYPE
	SYNTAX INTEGER {
		add-ports(1),
		clear-ports(2),
		set-admin-state(3)
	}
	ACCESS read-write
	STATUS mandatory
	DESCRIPTION
		"This object specifies the action that we apply on
		 a group. add-ports(1) adds port(s) to a group,
		 clear-ports(2) clears (delete) port(s) from a group,
		 and set-admin-state sets the Admin State of
		 the group."
	::= { groupSet 1 }


groupSetGroupID OBJECT-TYPE
	SYNTAX INTEGER {
		group-1(1),
		group-2(2),
		group-3(3),
		group-4(4),
		group-5(5),
		group-6(6),
		group-7(7),
		group-8(8),
		all-groups(255) -- only valid for groupSetAction of
				-- clear-ports(2)
		}
	ACCESS read-write
	STATUS mandatory
	DESCRIPTION
		"A group index that uniquely identifies this group. A port
		can be in zero, one, or more groups."
	::= { groupSet 2 }


groupSetSlotIndex OBJECT-TYPE
	SYNTAX INTEGER
	ACCESS read-write
	STATUS mandatory
	DESCRIPTION
		"This object specifies the slot number of the port(s) that
		are to be added/cleared to/from the group. This object should
		be set whenever add-ports(1) or clear-ports(2) are selected
		for groupSetAction.  Value 254 refers to all non-existing
		ports, and value 255 refers to all slots which are only valid
		when groupSetAction is clear-ports(2)."
	::= { groupSet 3 }

groupSetPortIndex OBJECT-TYPE
	SYNTAX INTEGER
	ACCESS read-write
	STATUS mandatory
	DESCRIPTION
		"This object specifies the port number of the port(s) that
		are to be added/cleared to/from the group. This object should
		be set whenever add-ports(1) or clear-ports(2) are selected
		for groupSetAction. Value 255 refers to all ports."
	::= { groupSet 4 }


groupSetAdminState OBJECT-TYPE
	SYNTAX INTEGER {
		enabled(1),
		disabled(2)
	}
	ACCESS read-write
	STATUS mandatory
	DESCRIPTION
		"This object specifies the Admin State that all the ports in
		the group defined by groupSetGroupID should be set to.
		This object should be set whenever set-admin-state(3) is
		selected for groupSetAction."
	::= { groupSet 5 }


--  Threshold Group

--	This group provides access to agent thresholding.
--	If the agent does not support thresholding, then
--	threshTable will have no entries.


threshTotalEntries OBJECT-TYPE
  SYNTAX INTEGER
  ACCESS read-only
  STATUS mandatory
  DESCRIPTION
	"The number of entries currently in threshTable."
    ::= { threshControl 1 }

threshMaxEntries OBJECT-TYPE
  SYNTAX INTEGER
  ACCESS read-only
  STATUS mandatory
  DESCRIPTION
	"The maximum number of entries in threshTable supported by
	this agent."
    ::= { threshControl 2 }

threshLastCreatedIndex OBJECT-TYPE
  SYNTAX INTEGER
  ACCESS read-only
  STATUS mandatory
  DESCRIPTION
	"The index of the last entry in threshTable created via index 255
	(see threshMode).  If none, this value will be zero."
    ::= { threshControl 3 }

threshAllMode OBJECT-TYPE
	SYNTAX INTEGER {
		enable(1),
		disable(2),
		clear(3)
		}
	ACCESS read-write
	STATUS mandatory
	DESCRIPTION
		"Provides the management station with a convenient way to set
		threshMode for all of the entries in ThreshTable.
		Setting threshAllMode to enable(1) or disable(2)
		will not cause new entries to be created; this
		will only affect entries that have presiously been created.
		Getting threshAllMode will always yield clear(3)."
	::= { threshControl 4 }

threshTable OBJECT-TYPE
    SYNTAX SEQUENCE OF ThreshEntry
    ACCESS not-accessible
    STATUS mandatory
    DESCRIPTION
	"A list of thresholding entries."
    ::= { thresh 2 }

threshEntry OBJECT-TYPE
    SYNTAX ThreshEntry
    ACCESS not-accessible
    STATUS mandatory
    DESCRIPTION
	"A collection of variables for controlling and monitoring a
	specific threshold."
    INDEX { threshIndex }
    ::= { threshTable 1 }

ThreshEntry ::= SEQUENCE {
    threshIndex		INTEGER,
    threshMode		INTEGER,
    threshDescription		DisplayString,
    threshObjectIdentifier	OBJECT IDENTIFIER,
    threshStatCategory  INTEGER,
    threshStatType		INTEGER,
    threshStatNetID		INTEGER,
    threshStatSlotIndex INTEGER,
    threshStatPortIndex INTEGER,
    threshStatStationAddr	MacAddress,
    threshInterval		INTEGER,
    threshCondition		INTEGER,
    threshValue		INTEGER,
    threshCurrentValue  INTEGER,
    threshStatus		INTEGER,
    threshTimeSinceLastTriggered	TimeTicks,
    threshActionType		INTEGER,
    threshActionData		INTEGER,
    threshActionPriority	INTEGER
}

threshIndex OBJECT-TYPE
  SYNTAX INTEGER
  ACCESS read-only
  STATUS mandatory
  DESCRIPTION
	"An index that uniquely identifies an entry in
	the thresh table.  The number of entries in olTRThreshTable
	is threshTotalEntries.  A new entry is created when a value is
	written to any object within the entry.  An entry is removed when
	threshMode is set to clear(3).
	Index 255 references a 'pseudo entry' that allows
	the management station to create a new entry without having to
	search for a clear entry.
	When threshMode for entry 255 is set to disable or enable,
	if there is no available (clear) entry, then the SNMP set-response will
	indicate a bad value error, otherwise the agent does the following:
	    - set the value of threshLastCreatedIndex to the index
		of the available entry
	    - copy the values currently in entry 255 to the available entry
	    - clear out entry 255."
  ::= { threshEntry 1 }

threshMode OBJECT-TYPE
	SYNTAX INTEGER {
		enable(1),
		disable(2),
		clear(3)
		}
	ACCESS read-write
	STATUS mandatory
	DESCRIPTION
		"The mode for this threshold.
		enable(1) indicates that this entry
		is in use and thresholding will be done.
		disable(2) indicates that this entry
		is in use but will no thresholding will be done.
		Setting threshMode to clear(3)  will cause this entry to be
		removed from the table."
--	DEFVAL {disable(2)}
	::= { threshEntry 2 }

threshDescription OBJECT-TYPE
	SYNTAX DisplayString (SIZE(0..40))
	ACCESS read-write
	STATUS mandatory
	DESCRIPTION
		"Description of the threshold to be sent with the
		ibm8250AboveThreshd trap."
	::= { threshEntry 3 }

threshObjectIdentifier OBJECT-TYPE
	SYNTAX OBJECT IDENTIFIER
	ACCESS read-write
	STATUS mandatory
	DESCRIPTION
		"The object identifier that specifies the statistic to be
		thresholded.  The statistic to be thresholded can be
		specified either by setting threshObjectIdentifier
		or by setting values of the threshStat group of variables.
		When threshObjectIdentifier is set, the agent changes
		the values of the threshStat group of variables
		to refer to the new statistic to be thresholded.
		Similarly, when a threshStat variable is set, the agent
		changes threshObjectIdentifier to refer to the new statistic
		to be thresholded.  A null object identifier (0.0) is used
		when no statistic is specified."
	::= { threshEntry 4 }

threshStatCategory OBJECT-TYPE
	SYNTAX INTEGER {
		other(1),
		network(2),
		port(3),
		station(4)
	}
	ACCESS read-write
	STATUS mandatory
	DESCRIPTION
		"Specifies the category of statistic to be thresholded.
		When threshStatCategory is network(2) or station(4),
		threshStatNetID must also be specified and
		threshStatSlotIndex will be overwritten as well.
		When threshStatCategory is station(4),
		threshStatStation must be specified.
		When threshStatCategory is port(3), threshStatSlotIndex
		and threshStatPortIndex must be specified.  Modifying
		threshStatSlotIndex in this case will cause
		threshStatNetID to be overwritten as well."

--	DEFVAL {network(2)}
	::= { threshEntry 5 }

threshStatType OBJECT-TYPE
	SYNTAX INTEGER {
		other(1),
		frames(2),
		octets(3),
		broadcast-frames(4),
		multicast-frames(5),
		error-frames(6),
		tr-net-soft-errors(7),
		tr-net-hard-errors(8)
	}
	ACCESS read-write
	STATUS mandatory
	DESCRIPTION
		"Specifies the type of statistic to be thresholded.
		error-frames(6) is valid only when threshStatCategory is
		port(3) or station(4).  tr-net-soft-errors(7) or
		tr-net-hard-errors(8) is valid only when threshStatCategory
		is network(2).  Note that tr-net-soft-errors(7) and
		tr-net-hard-errors(8) refer to dot5StatsSoftErrors
		and dot5StatsHardErrors, respectively.  The other choices
		refer for items in the trTraf tables."
--	DEFVAL {frames(2)}
	::= { threshEntry 6 }

threshStatNetID OBJECT-TYPE
	SYNTAX INTEGER {
		other(1),
		isolated(2),
		token-ring-1(9),
		token-ring-2(10),
		token-ring-3(11),
		token-ring-4(12),
		token-ring-5(13),
		token-ring-6(14),
		token-ring-7(15),
		agent-network(255)
	}
	ACCESS read-write
	STATUS mandatory
	DESCRIPTION
		"When threshStatCategory is network(2) or station(4),
		specifies the network of statistic to be thresholded.
		If the agent is capable of collecting statistics only for
		the network that it is attached to, threshStatNetID can
		be set to agent-network(255); the agent will change
		threshStatNetID to reflect the network that the agent
		is currently attached to.  If threshStatType is
		tr-net-soft-errors(7) or tr-net-hard-errors(8) the
		agent will change threshStatNetID to other(1).
		Note that when this variable is set, threshStatSlotIndex
		is overwritten as well."
--	DEFVAL {agent-network(255)}
	::= { threshEntry 7 }

threshStatSlotIndex OBJECT-TYPE
	SYNTAX INTEGER
	ACCESS read-write
	STATUS mandatory
	DESCRIPTION
		"When threshStatCategory is port(3), specifies the
		slot index of the port of statistic to be thresholded.
		Note that when this variable is set, threshStatNetID
		is overwritten as well."
	::= { threshEntry 8 }

threshStatPortIndex OBJECT-TYPE
	SYNTAX INTEGER
	ACCESS read-write
	STATUS mandatory
	DESCRIPTION
		"When threshStatCategory is port(3), specifies the
		port index of the port of statistic to be thresholded."
	::= { threshEntry 9 }

threshStatStationAddr OBJECT-TYPE
	SYNTAX MacAddress
	ACCESS read-write
	STATUS mandatory
	DESCRIPTION
		"When threshStatCategory is station(4), specifies the
		MAC address of the station of statistic to be thresholded."
	::= { threshEntry 10 }

threshInterval OBJECT-TYPE
	SYNTAX INTEGER
	ACCESS read-write
	STATUS mandatory
	DESCRIPTION
		"Specifies the length of the thresholding period in seconds.
		Minimum length is 5 seconds; maximum is 86400 seconds
		(24 hours)."
--	DEFVAL {60}
	::= { threshEntry 11 }

threshCondition OBJECT-TYPE
	SYNTAX INTEGER {
		delta-above(1)
	}
	ACCESS read-write
	STATUS mandatory
	DESCRIPTION
		"Specifies the type of conditional comparison for the
		threshold."
--	  Possible future values for threshCondition: delta-below,
--	  absolute-above, absolute-below
--	DEFVAL {delta-above(1)}
	::= { threshEntry 12 }

threshValue OBJECT-TYPE
	SYNTAX INTEGER
	ACCESS read-write
	STATUS mandatory
	DESCRIPTION
	    "At the end of each thresholding interval (threshInterval
	    seconds), threshCurrentValue is compared against
	    threshValue (unsigned).
	    When threshType is delta-above(1):
		If threshStatus is valid(4), and threshCurrentValue is
		above threshValue, and threshMode is enabled,
		then a ibm8250AboveThreshd trap will be sent.
		Another ibm8250AboveThreshd trap will not be sent until
		threshCurrentValue drops to less than or equal to
		threshValue and then again exceeds it."
--	DEFVAL { 0 }
	::= { threshEntry 13 }

threshCurrentValue OBJECT-TYPE
	SYNTAX INTEGER
	ACCESS read-only
	STATUS mandatory
	DESCRIPTION
	    "When threshType is delta-exceed(1):
		The most recent delta value of threshStatObjectIdentifier
		(i.e. value of threshStatObjectIdentifier at the end of
		the interval minus the value of threshStatObjectIdentifier
		at the beginning of the interval).
	    If threshStatus is not valid(4), threshCurrentValue will be 0."
	::= { threshEntry 14 }

threshStatus OBJECT-TYPE
	SYNTAX INTEGER {
		no-statistic-specified(1),
		statistic-not-accessible(2),
		not-yet-available(3),
		valid(4)
	}
	ACCESS read-only
	STATUS mandatory
	DESCRIPTION
	    "When threshType is delta-exceed(1):
		If threshStatObjectIdentifier has not yet been specified,
		threshStatus will be no-statistic-specified(1).
		If the first interval has not yet completed,
		threshStatus will be not-yet-available(2).
		If object referenced by threshStatObjectIdentifier is not
		accessible, threshStatus will be not-accessible(3).
		Otherwise threshStatus will be valid(4)."
	::= { threshEntry 15 }

threshTimeSinceLastTriggered OBJECT-TYPE
  SYNTAX TimeTicks
  ACCESS read-only
  STATUS mandatory
  DESCRIPTION
	"Time in TimeTicks that has elapsed since a ibm8250AboveThreshd trap
	associated with this ThreshEntry was last sent.
	If never sent, this value shall be zero."
    ::= { threshEntry 16 }

threshActionType OBJECT-TYPE
	SYNTAX INTEGER {
		trap-only(1),
		run-script-only(2),
		trap-run-script(3)
	}
	ACCESS read-write
	STATUS mandatory
	DESCRIPTION
		"The action to be performed when the threshold is triggered."
    ::= { threshEntry 17 }

threshActionData OBJECT-TYPE
	SYNTAX INTEGER
	ACCESS read-write
	STATUS mandatory
	DESCRIPTION
		"Additional information to be sent with the
		ibm8250AboveThreshd trap.  In the case of
		scripts, this object will contain the script
		number to be executed."
    ::= { threshEntry 18 }

threshActionPriority OBJECT-TYPE
	SYNTAX INTEGER {
		low(1),
		medium(2),
		high(3)
	}
	ACCESS read-write
	STATUS mandatory
	DESCRIPTION
		"The priority for this entry.  Provided for use by the
		network management station (NMS) - not interpreted by
		the agent."
--	DEFVAL {low(1)}
    ::= { threshEntry 19 }


--
-- IBM 8260 Power Group
--
-- This group is used for managing the
-- power in the IBM 8260 hub.

--
-- Hub power mode
--
ocPowerModeAdminStatus OBJECT-TYPE
	SYNTAX INTEGER {
		fault-tolerant(1),
		not-fault-tolerant(2)
		}
	ACCESS read-write
	STATUS mandatory
	DESCRIPTION
		"The desired state of the hub power mode. Setting
		 this object to fault-tolerant(1) reserves one power
		 supply's worth of power. The agent will not allow
		 a manager to change the mode to fault-tolerant(1) if
		 there is not enough power available or there is only
		 one operational power supply, and invalidData error
		 will be returned. In this case, the manager must
		 explicitly power down modules until there is enough
		 power, or add additional power supplies."
	::= { ocPowerControl 1 }

ocPowerModeOperStatus OBJECT-TYPE
	SYNTAX INTEGER {
		fault-tolerant(1),
		not-fault-tolerant(2)
		}
	ACCESS read-only
	STATUS mandatory
	DESCRIPTION
		" The current operating status of the power mode. "
	::= { ocPowerControl 2 }

ocPowerOverheatPowerDownMode OBJECT-TYPE
	SYNTAX INTEGER {
		enable(1),
		disable(2)
		}
	ACCESS read-write
	STATUS mandatory
	DESCRIPTION
		"This object is used to administer and report the
		 hub overheat-power-down mode. Setting this object
		 to enable(1) will power down the hub in an overheat
		 situation."
	::= { ocPowerControl 3 }

--
--  Hub backplane power
--
ocPowerOutputTable OBJECT-TYPE
	SYNTAX SEQUENCE OF OcPowerOutputEntry
	ACCESS not-accessible
	STATUS mandatory
	DESCRIPTION
		"A list of all power supplies budget combined, indexed
		 with respect to the voltage type which is supplied by
		 all operational power supplies in the hub."
	::= { ocPower 2 }

ocPowerOutputEntry OBJECT-TYPE
	SYNTAX OcPowerOutputEntry
	ACCESS not-accessible
	STATUS mandatory
	DESCRIPTION
		"Values to describe backplane power outputs."
	INDEX { ocPowerOutputType }
	::= { ocPowerOutputTable 1 }

OcPowerOutputEntry ::=
	SEQUENCE {
		ocPowerOutputType
			INTEGER,
		ocPowerOutputVoltageLevel
			Gauge,
		ocPowerOutputWattageCapacity
			Gauge,
		ocPowerOutputWattageConsumed
			Gauge,
		ocPowerOutputWattageAvailable
			Gauge,
		ocPowerOutputUnmanagedWattageAlloc
			Gauge
		}

ocPowerOutputType OBJECT-TYPE
	SYNTAX INTEGER {
		plusFiveVolt(1),	-- + 5 Volt
		minusFiveVolt(2),	-- - 5 Volt
		plusTwelveVolt(3),	-- +12 Volt
		minusTwelveVolt(4),	-- -12 Volt
		plusTwoVolt(5)		-- + 2 Volt
		}
	ACCESS  read-only
	STATUS  mandatory
	DESCRIPTION
		"The type of power with respect to the voltage
		 supplied."
	::= { ocPowerOutputEntry 1 }

ocPowerOutputVoltageLevel OBJECT-TYPE
	SYNTAX Gauge
	ACCESS read-only
	STATUS mandatory
	DESCRIPTION
		"In millivolts (1/1000 Volt), the actual voltage
		 level for this voltage type supplied by all
		 operational power supplies combined."
	::= { ocPowerOutputEntry 2 }

ocPowerOutputWattageCapacity OBJECT-TYPE
	SYNTAX Gauge
	ACCESS read-only
	STATUS mandatory
	DESCRIPTION
		"In hundredths of a Watt (1/100 Watt), the maximum
		 wattage of a particular voltage type that could be
		 supplied by all operational power supplies combined,
		 (i.e. the power rating)."
	::= { ocPowerOutputEntry 3 }

ocPowerOutputWattageConsumed OBJECT-TYPE
	SYNTAX Gauge
	ACCESS read-only
	STATUS mandatory
	DESCRIPTION
		"In hundredths of a Watt (1/100 Watt), the wattage
		 consumed by all of the hub modules. If the
		 power mode is not-fault-tolerant, then this value
		 equals the power capacity minus available power. If
		 the power mode is fault-tolerant, this value is equal
		 to power capacity minus available power minus reserved
		 power ( e.g. consumed power = capacity - available -
		 reserved)."
	::= { ocPowerOutputEntry 4 }

ocPowerOutputWattageAvailable OBJECT-TYPE
	SYNTAX Gauge
	ACCESS read-only
	STATUS mandatory
	DESCRIPTION
		"In hundredths of a Watt (1/100 Watt), the wattage
		 available to power up modules. The power mode
		 (fault-tolerant / not-fault-tolerant) is taken
		 into account to calculate this value. This value
		 will increase if the power mode is switched from
		 fault-tolerant to not-fault-tolerant and vice
		 versa."
	::= { ocPowerOutputEntry 5 }

ocPowerOutputUnmanagedWattageAlloc OBJECT-TYPE
	SYNTAX Gauge
	ACCESS read-only
	STATUS mandatory
	DESCRIPTION
		"In hundredths of a Watt (1/100 Watt), the total
		 power budget that is allocated for modules that
		 do not support power management, (e.g. Hub
		 modules)."
	::= { ocPowerOutputEntry 6 }

--
-- Module power configuration
--
ocPowerSlotTable OBJECT-TYPE
	SYNTAX SEQUENCE OF OcPowerSlotEntry
	ACCESS not-accessible
	STATUS mandatory
	DESCRIPTION
		"A table that contains power management information
		 for each non-empty slot in the hub."
	::= { ocPower 3  }

ocPowerSlotEntry OBJECT-TYPE
	SYNTAX OcPowerSlotEntry
	ACCESS not-accessible
	STATUS mandatory
	DESCRIPTION
		"A list of power information for each non-empty
		 slot in the hub."
	INDEX { ocPowerSlotIndex }
	::= { ocPowerSlotTable 1 }

OcPowerSlotEntry ::=
	SEQUENCE {
		 ocPowerSlotIndex
			INTEGER,
		 ocPowerSlotClass
			INTEGER,
		 ocPowerSlotAdminStatus
			INTEGER,
		 ocPowerSlotOperStatus
			INTEGER
		 }

ocPowerSlotIndex OBJECT-TYPE
	SYNTAX INTEGER
	ACCESS read-only
	STATUS mandatory
	DESCRIPTION
		"The unique slot number that identifies the
		 module associated with this power entry."
	::= { ocPowerSlotEntry 1 }

ocPowerSlotClass OBJECT-TYPE
	SYNTAX INTEGER {
		one(1),
		two(2),
		three(3),
		four(4),
		five(5),
		six(6),
		seven(7),
		eight(8),
		nine(9),
		ten(10),
		not-applicable(11)
		}
	ACCESS read-write
	STATUS mandatory
	DESCRIPTION
		"The slot power class. It ranges from 1 to 10,
		 where 10 is the highest. The power class is a
		 determining factor to power up or down a module.
		 The class is non preemptive object, e.g. inserting
		 or enabling a higher class module will not
		 result in powering down lower class modules if
		 the power budget is not sufficeint to power up
		 this module. If there is more than one module to
		 be powered up, those with higher class will
		 be powered up first. If the power budget drops,
		 i.e. a power supply fails, then lower class
		 modules may be powered down to stay within the
		 power budget. If there is more than one slot with
		 the same class, the selection among those slots
		 will be based on the slot index, where slots with
		 lower indices are selected first. Class not-applicable(11)
		 will be returned for non-manageable modules (i.e. Hub
		 modules). Setting this object to not-appicable(11) will
		 return invalidData error."
	::= { ocPowerSlotEntry 2 }

ocPowerSlotAdminStatus OBJECT-TYPE
	SYNTAX  INTEGER {
		enable(1),  -- enable slot power
		disable(2)  -- disable slot power
		}
	ACCESS read-write
	STATUS mandatory
	DESCRIPTION
		"The current desired power state of the module. To power
		 up a module, its state should be set to enable(1).
		 Setting this object to disable(2) disables the slot
		 power. Once disabled, a module power must be explicitly
		 enabled to restore operation."
	::= { ocPowerSlotEntry 3 }

ocPowerSlotOperStatus OBJECT-TYPE
	SYNTAX INTEGER {
		enabled(1),		-- Slot power is enabled
		disabled(2),		-- Slot power is disabled
		insufficient-power(3),  -- Slot power up not possible
		enabled-always(4)	-- Slot power is enabled always
		}
	ACCESS read-only
	STATUS mandatory
	DESCRIPTION
		"The current operational power status of the module. The
		 module will be marked with insufficient-power(3) if it is
		 eligible to receive power but due to power constraint it
		 is not powered up. The enabled(1) state will be reported if
		 the module was actually powered up. The disabled(2) state
		 is reported if the module was not powered up, not in
		 insufficient-power state, and not eligible to receive power.
		 When a module is inserted into a slot, its state will
		 be reported as insufficient-power(3) if it is eligible to
		 receive power. If there is not enough power available in
		 the budget, this state will remain until the power budget
		 rises to accommodate the module power requirement, resulting
		 in powering up the module and hence, switching its operational
		 state to enabled(1). The status enabled-always(4) will be
		 returned for slots with power state that can not be set.
		 (i.e. Hub Modules, slot with master management module)."
	::= { ocPowerSlotEntry 4 }

--
-- IBM 8260 Inventory Group
--
-- This group reflects inventory information about
-- components in the IBM 8260 hub.
--

--
-- Hub chassis information
--
ocInvHubType OBJECT-TYPE
	SYNTAX DisplayString (SIZE(1..32))
	ACCESS read-only
	STATUS mandatory
	DESCRIPTION
		"The hub type (i.e. model number) of the hub.  An instance
		for which information is not valid will return 'invalid
		EEPROM!'."
	::= { ocInvHub 1 }

ocInvHubSerialNo OBJECT-TYPE
	SYNTAX DisplayString (SIZE(1..32))
	ACCESS read-only
	STATUS mandatory
	DESCRIPTION
		"The serial number of the hub.  An instance for which
		information is not valid will return 'invalid EEPROM!'."
	::= { ocInvHub 2 }

ocInvHubHWVer OBJECT-TYPE
	SYNTAX DisplayString (SIZE(1..32))
	ACCESS read-only
	STATUS mandatory
	DESCRIPTION
		"The revision number of the hardware of the hub.  An instance
		for which information is not valid will return 'invalid
		EEPROM!'."
	::= { ocInvHub 3 }

ocInvHubMfr OBJECT-TYPE
	SYNTAX DisplayString (SIZE(1..32))
	ACCESS read-only
	STATUS mandatory
	DESCRIPTION
		"The company name that manufactured this hub.  An instance
		for which information is not valid will return 'invalid
		EEPROM!."
	::= { ocInvHub 4 }

ocInvHubMfrDate OBJECT-TYPE
	SYNTAX DisplayString (SIZE(6))
	ACCESS read-only
	STATUS mandatory
	DESCRIPTION
		"The date in yymmdd format that this unit was manufactured.
		 An instance for which information is not valid will return
		 'invalid EEPROM!'."
	::= { ocInvHub 5 }


--
-- IBM 8260 Modules inventory information
--
-- Contains information about the hub modules. The modules
-- information are organized as a base-one matrix. That is, a module,
-- motherboard or daughter card, can be located by a pair of primitives:
-- slot index and subslot index (i.e. <slot>.<subslot>)
--
-- ocInvModTable
--
ocInvModTable OBJECT-TYPE
	SYNTAX SEQUENCE OF OcInvModEntry
	ACCESS not-accessible
	STATUS mandatory
	DESCRIPTION
		"A list of inventory information related to a module,
		 indexed with respect to slot and subslot location numbers."
	::= { ocInvMods 1 }

ocInvModEntry OBJECT-TYPE
	SYNTAX OcInvModEntry
	ACCESS not-accessible
	STATUS mandatory
	DESCRIPTION
		"Values to describe a module inventory items."
	INDEX { ocInvModSlotIndex, ocInvModSubSlotIndex }
	::= { ocInvModTable 1 }

OcInvModEntry ::=
	SEQUENCE {
		ocInvModSlotIndex
			INTEGER,
		ocInvModSubSlotIndex
			INTEGER,
		ocInvModModel
			DisplayString,
		ocInvModSerialNo
			DisplayString,
		ocInvModHWVer
			DisplayString,
		ocInvModSWVer
			DisplayString,
		ocInvModSWBootVer
			DisplayString,
		ocInvModMfr
			DisplayString,
		ocInvModMfrDate
			DisplayString

		}

ocInvModSlotIndex OBJECT-TYPE
	SYNTAX INTEGER
	ACCESS read-only
	STATUS mandatory
	DESCRIPTION
		"The slot number where this Module is located."
	::= { ocInvModEntry 1 }

ocInvModSubSlotIndex OBJECT-TYPE
	SYNTAX INTEGER
	ACCESS read-only
	STATUS mandatory
	DESCRIPTION
		"The subslot number where this Module is located. It is
		 associated with a slot number. Motherboards are always
		 located in subslot one, (e.g. <slot>.1). However,
		 daughter cards can reside on any subslot within the range
		 (2 ... 8), (e.g. <slot>.<2 .. 8>)."
	::= { ocInvModEntry 2 }

ocInvModModel OBJECT-TYPE
	SYNTAX DisplayString (SIZE(1..32))
	ACCESS read-only
	STATUS mandatory
	DESCRIPTION
		"This Module model number. If the instance value is
		 unknown, Hub will be returned."
	::= { ocInvModEntry 3 }

ocInvModSerialNo OBJECT-TYPE
	SYNTAX DisplayString (SIZE(1..32))
	ACCESS read-only
	STATUS mandatory
	DESCRIPTION
		"This Module serial number. If the instance value
		 is unknown, N/A will be returned."
	::= { ocInvModEntry 4 }

ocInvModHWVer OBJECT-TYPE
	SYNTAX DisplayString (SIZE(1..32))
	ACCESS read-only
	STATUS mandatory
	DESCRIPTION
		"The revision number of the hardware on this module.
		 If the instant value is unknown, N/A will be returned."
	::= { ocInvModEntry 5 }

ocInvModSWVer OBJECT-TYPE
	SYNTAX DisplayString (SIZE(1..32))
	ACCESS read-only
	STATUS mandatory
	DESCRIPTION
		"The revision number of the software on this module.
		 If the instant value is unknown, N/A will be
		 returned."
	::= { ocInvModEntry 6 }

ocInvModSWBootVer OBJECT-TYPE
	SYNTAX DisplayString (SIZE(1..32))
	ACCESS read-only
	STATUS mandatory
	DESCRIPTION
		"The revision number of the boot software on this module.
		 If the instant value is unknown, N/A will be returned."
	::= { ocInvModEntry 7 }

ocInvModMfr OBJECT-TYPE
	SYNTAX DisplayString (SIZE(1..32))
	ACCESS read-only
	STATUS mandatory
	DESCRIPTION
		"The company name that manufactured this module. If the
		 instant value is unkonwn, N/A will be returned."
	::= { ocInvModEntry 8 }

ocInvModMfrDate OBJECT-TYPE
	SYNTAX DisplayString (SIZE(6))
	ACCESS read-only
	STATUS mandatory
	DESCRIPTION
		"The date in yymmdd format that this module was manufactured.
		 If the instant value is unknown, N/A will be returned."
	::= { ocInvModEntry 9 }


--
-- The pS2 MIB:
--
-- The following group is used to manage PS/2 attributes in
-- the Hub. It provides detailed information about the hardware
-- configuration and adapter cards installed on the PS/2. In
-- addition it provides an indication of the software installed
-- on the PS/2.
--
-- This information must be set manually from the console interface
-- on the network management module, or remotely via its Telnet
-- interface.
--
--
--			PS2 Groups
--
-- Under the pS2 branch exists:
--
--     pS2Info      - system information about the PS/2
--     pS2McaTable  - a table of information concerning
--			Micro channel adapter cards in the PS/2
--     pS2ApplTable - a table of information decsribing the
--			software applications availabl on the PS/2
--


pS2Info OBJECT IDENTIFIER ::= { pS2 1 }

--
--			pS2Info
--
--
-- System Information concerning the PS/2
--
--

pS2OperatingSystem OBJECT-TYPE
	SYNTAX DisplayString (SIZE(0..32))
	ACCESS read-only
	STATUS mandatory
	DESCRIPTION
		"The type of operating system current
		including its version and release numbers,
		currently executing on the PS/2."
	::= { pS2Info 1 }

pS2FixedDiskSize OBJECT-TYPE
	SYNTAX DisplayString (SIZE(0..32))
	ACCESS read-only
	STATUS mandatory
	DESCRIPTION
		"The size in of Fixed Disk Memory currently
		installed on the PS/2."
	::= { pS2Info 2 }

pS2RamSize OBJECT-TYPE
	SYNTAX DisplayString (SIZE(0..32))
	ACCESS read-only
	STATUS mandatory
	DESCRIPTION
		"The size in of Random Access Memory
		currently installed on the PS/2."
	::= { pS2Info 3 }

--
--			pS2McaTable
--
--
-- Information about adapter cards that may be installed
-- in the Micro channel adapter card payload portion of
-- the hub.
--

pS2McaTable OBJECT-TYPE
	SYNTAX  SEQUENCE OF PS2McaEntry
	ACCESS  not-accessible
	STATUS  mandatory
	DESCRIPTION
		"A table of software application information
		associated with the PS/2."
	::= { pS2 2 }

pS2McaEntry OBJECT-TYPE
	SYNTAX  PS2McaEntry
	ACCESS  not-accessible
	STATUS  mandatory
	DESCRIPTION
		"A profile of a specific software application
		associated with this PS/2."
	INDEX	{ pS2McaIndex }
	::= { pS2McaTable 1 }

PS2McaEntry ::=
	SEQUENCE {
		pS2McaIndex
			INTEGER,
		pS2McaDescription
			DisplayString,
		pS2McaSlotConnectPoint
			INTEGER,
		pS2McaPortConnectPoint
			INTEGER,
		pS2McaMacAddress
			OCTET STRING
		}

pS2McaIndex OBJECT-TYPE
	SYNTAX INTEGER
	ACCESS read-only
	STATUS mandatory
	DESCRIPTION
		"The index for this software application."
	::= { pS2McaEntry 1 }

pS2McaDescription   OBJECT-TYPE
	SYNTAX  DisplayString (SIZE(0..32))
	ACCESS  read-only
	STATUS  mandatory
	DESCRIPTION
		"A description of the software application."
	::= { pS2McaEntry 2 }

pS2McaSlotConnectPoint OBJECT-TYPE
	SYNTAX INTEGER
	ACCESS read-only
	STATUS mandatory
	DESCRIPTION
		"The slot number of a module within this
		Hub chassis to which this
		Micro channel Adapter Card is connected.
		If not connected to any Hub module
		module, the object value is zero."
	::= { pS2McaEntry 3 }

pS2McaPortConnectPoint OBJECT-TYPE
	SYNTAX INTEGER
	ACCESS read-only
	STATUS mandatory
	DESCRIPTION
		"The port number of a module within this
		Hub chassis to which this
		Micro channel Adapter Card is connected.
		If not connected to any Hub module
		module, the object value is zero."
	::= { pS2McaEntry 4 }

pS2McaMacAddress   OBJECT-TYPE
	SYNTAX OCTET STRING (SIZE(6))
	ACCESS  read-only
	STATUS  mandatory
	DESCRIPTION
		"The MAC Address of the Micro channel
		adapter card installed this PS/2 Micro
		channel Adapter Card slot. If no MAC
		address is defined this string is
		encoded as a zero length string."
	::= { pS2McaEntry 5 }

--
--			pS2ApplTable
--
--
-- Information about software applications that may be
-- installed on the PS/2.
--
--

pS2ApplTable OBJECT-TYPE
	SYNTAX  SEQUENCE OF PS2ApplEntry
	ACCESS  not-accessible
	STATUS  mandatory
	DESCRIPTION
		"A table of software application information
		associated with the PS/2."
	::= { pS2 3 }

pS2ApplEntry OBJECT-TYPE
	SYNTAX  PS2ApplEntry
	ACCESS  not-accessible
	STATUS  mandatory
	DESCRIPTION
		"A profile of a specific software application
		associated with this PS/2."
	INDEX	{ pS2ApplIndex }
	::= { pS2ApplTable 1 }

PS2ApplEntry ::=
	SEQUENCE {
		pS2ApplIndex
			INTEGER,
		pS2ApplDescription
			DisplayString
		}

pS2ApplIndex OBJECT-TYPE
	SYNTAX INTEGER
	ACCESS read-only
	STATUS mandatory
	DESCRIPTION
		"The index for this software application."
	::= { pS2ApplEntry 1 }

pS2ApplDescription   OBJECT-TYPE
	SYNTAX  DisplayString (SIZE(0..32))
	ACCESS  read-only
	STATUS  mandatory
	DESCRIPTION
		"A description of the software application."
	::= { pS2ApplEntry 2 }



-- The net Group

-- This group represents information about Hub networks in general.

netDPTable OBJECT-TYPE
	SYNTAX SEQUENCE OF NetDPEntry
	ACCESS not-accessible
	STATUS mandatory
	DESCRIPTION
		"A table that contains information linking
		physical backplane allocation to logical
		networks. This information is useful:

			(1) to determine the physical allocation
			of networks on the backplane, and

			(2) to determine the remaining capacity of
			the backplane for future network growth.

		Since unknown modules are managed via dip
		switches, this is useful in order to set the
		dips to the appropriate settings.

		Ethernet is a bus architecture.  Once a path is
		allocated, all modules and ports can access that
		path.

		Token Ring and FDDI are ring architectures.
		Each module on a ring requires a path.  Therefore,
		4 paths could be used to link 4 modules together
		on one ring, or 2 modules on 2 separate rings.
		It is possible to have a module allocated to
		a ring (and thus a data path) without linking
		to another module.

		These rules can be used to determine the remaining
		capacity for network growth."
	::= { net 1 }

netDPEntry OBJECT-TYPE
	SYNTAX NetDPEntry
	ACCESS not-accessible
	STATUS mandatory
	DESCRIPTION
		"A list of information about each data path in the
		concentrator."
	INDEX { netDPDataPath }
	::= { netDPTable 1 }

NetDPEntry ::=
	SEQUENCE {
		netDPDataPath
			INTEGER,
		netDPNetID
			INTEGER
		}

netDPDataPath OBJECT-TYPE
	SYNTAX INTEGER {
		ethernet-path-1(6), -- channel 1
		ethernet-path-2(7), -- channel 2
		ethernet-path-3(8), -- channel 3
		token-ring-path-1(9),
		token-ring-path-2(10),
		token-ring-path-3(11),
		token-ring-path-4(12),
		token-ring-path-5(13),
		token-ring-path-6(14),
		token-ring-path-7(15),
		token-ring-path-8(16),
		token-ring-path-9(17),
		token-ring-path-10(18),
		token-ring-path-11(19),
		token-ring-path-12(20),
		token-ring-path-13(21),
		token-ring-path-14(22),
		token-ring-path-15(23),
		fddi-path-1(24),
		fddi-path-2(25),
		fddi-path-3(26),
		fddi-path-4(27),
		fddi-path-5(28),
		fddi-path-6(29),
		fddi-path-7(30),
		fddi-path-8(31),
		ethernet-path-4(32),
		ethernet-path-5(33),
		ethernet-path-6(34),
		ethernet-path-7(35),
		ethernet-path-8(36)
		}
	ACCESS read-only
	STATUS mandatory
	DESCRIPTION
		"The data path on the backplane.  Data paths between
		different protocols overlap.  That is, an ethernet data
		path will overlap with multiple token ring and fddi data
		paths. "
	::= { netDPEntry 1 }

netDPNetID OBJECT-TYPE
	SYNTAX INTEGER {
		notUsed(1),		-- available for use
		otherProto(2),		-- another protocol is using
					-- these resources
		ethernet-1(6),
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19)
		}
	ACCESS  read-only
	STATUS mandatory
	DESCRIPTION
		"The network that this data path corresponds to.
		If the data path is not being used at all, notUsed(1)
		is the return value.  If the data path is being used
		by another protocol, then otherProto(2) is the
		return value."
	::= { netDPEntry 2 }


--
-- The following objects comprise the oldest style of security.
-- They are left here for backward compatibility with existing
-- applications; however, this group will not be enhanced.
--
netSecurityMACTable OBJECT-TYPE
	SYNTAX SEQUENCE OF NetSecurityMACEntry
	ACCESS not-accessible
	STATUS mandatory
	DESCRIPTION
		"A table of security configuration parameters and MAC
		addresses associated with every port with security
		configured in the concentrator."
	::= { net 2 }

netSecurityMACEntry OBJECT-TYPE
	SYNTAX NetSecurityMACEntry
	ACCESS not-accessible
	STATUS mandatory
	DESCRIPTION
		"A list of security configuration parameters and MAC
		addresses associated with each port with security
		configured in the concentrator."
	INDEX { netSecurityMACSlotIndex, netSecurityMACPortIndex,
		netSecurityMACAddress }
	::= { netSecurityMACTable 1 }

NetSecurityMACEntry ::=
	SEQUENCE {
		netSecurityMACSlotIndex
			INTEGER,
		netSecurityMACPortIndex
			INTEGER,
		netSecurityMACAddress
			MacAddress,
		netSecurityMACMode
			INTEGER,
		netSecurityMACStatus
			INTEGER
		 }
netSecurityMACSlotIndex OBJECT-TYPE
	 SYNTAX INTEGER
	 ACCESS read-only
	 STATUS mandatory
	 DESCRIPTION
		 "The slot number that contains this port."
	 ::= { netSecurityMACEntry 1 }

netSecurityMACPortIndex OBJECT-TYPE
	 SYNTAX INTEGER
	 ACCESS read-only
	 STATUS mandatory
	 DESCRIPTION
		 "The port number within this slot."
	 ::= { netSecurityMACEntry 2 }

netSecurityMACAddress OBJECT-TYPE
	 SYNTAX MacAddress
	 ACCESS read-write
	 STATUS mandatory
	 DESCRIPTION
		 "The security MAC address assigned to this port."
	 ::= { netSecurityMACEntry 3 }

netSecurityMACMode OBJECT-TYPE
	SYNTAX INTEGER {
		enabled(1),
		disabled(2)
		}
	ACCESS read-write
	STATUS mandatory
	DESCRIPTION
		"The desired security mode for this port/address."
--	DEFVAL {disabled(2)}
	::= { netSecurityMACEntry 4 }

netSecurityMACStatus OBJECT-TYPE
	SYNTAX INTEGER {
		valid(1),
		invalid(2)
		}
	ACCESS read-write
	STATUS mandatory
	DESCRIPTION
		"Each instance of the netSecurityMACTable associated
		with this netSecurityMACEntry (slot, port, and address)
		will be deleted by the agent if this netSecurityMACEntry
		is not equal to valid(1).  Initial creation of instances
		occurs via a set operation on a specific slot/port/address."
--	DEFVAL {valid(1)}
	::= { netSecurityMACEntry 5 }


--
-- The following groups of objects comprise the new style of security
-- (to be compared with the old style defined above).  This includes a
-- specific table for control parameters per port, objects for autolearning,
-- and a cache of previous intrusion attempts.
--

netSec  OBJECT IDENTIFIER ::= { net 3 }


netSecAddrTable OBJECT-TYPE
	SYNTAX SEQUENCE OF NetSecAddrEntry
	ACCESS not-accessible
	STATUS mandatory
	DESCRIPTION
		"A table of security MAC addresses."
	::= { netSec 1 }

netSecAddrEntry OBJECT-TYPE
	SYNTAX NetSecAddrEntry
	ACCESS not-accessible
	STATUS mandatory
	DESCRIPTION
		"Security MAC addresses indexed by slot, port, and MAC
		address."
	INDEX {netSecAddrSlotIndex, netSecAddrPortIndex,
		netSecAddrAddress }
	::= { netSecAddrTable 1 }

NetSecAddrEntry ::=
	SEQUENCE {
		netSecAddrSlotIndex
			INTEGER,
		netSecAddrPortIndex
			INTEGER,
		netSecAddrAddress
			MacAddress,
		netSecAddrStatus
			INTEGER
		}

netSecAddrSlotIndex OBJECT-TYPE
	SYNTAX INTEGER
	ACCESS read-only
	STATUS mandatory
	DESCRIPTION
		"The slot number index (used along with the port and address
		indices)."
	::= { netSecAddrEntry 1 }

netSecAddrPortIndex OBJECT-TYPE
	SYNTAX INTEGER
	ACCESS read-only
	STATUS mandatory
	DESCRIPTION
		"The port number index (used along with the slot and address
		indices)."
	::= { netSecAddrEntry 2 }

netSecAddrAddress OBJECT-TYPE
	SYNTAX MacAddress
	ACCESS read-write
	STATUS mandatory
	DESCRIPTION
		"The security MAC address index (used along with the slot and
		port indices).  Note that there may be multiple addresses
		associated with a single port."
	::= { netSecAddrEntry 3 }

netSecAddrStatus OBJECT-TYPE
	SYNTAX INTEGER {
		valid(1),
		invalid(2)
		}
	ACCESS read-write
	STATUS mandatory
	DESCRIPTION
		"Setting this object to valid(1) will cause the
		corresponding security MAC address to be associated
		with the given port.  Setting this object to
		invalid(2) will clear the corresponding MAC address
		for the given port."
	::= { netSecAddrEntry 4 }


netSecControlTable OBJECT-TYPE
	SYNTAX SEQUENCE OF NetSecControlEntry
	ACCESS not-accessible
	STATUS mandatory
	DESCRIPTION
		"A table of security configuration parameters pertaining
		to a specific port."
	::= { netSec 2 }

netSecControlEntry OBJECT-TYPE
	SYNTAX NetSecControlEntry
	ACCESS not-accessible
	STATUS mandatory
	DESCRIPTION
		"Security configuration parameters pertaining to a specific
		port (indexed by slot and port)."
	INDEX { netSecControlSlotIndex, netSecControlPortIndex }
	::= { netSecControlTable 1 }

NetSecControlEntry ::=
	SEQUENCE {
		netSecControlSlotIndex
			INTEGER,
		netSecControlPortIndex
			INTEGER,
		netSecControlMode
			INTEGER,
		netSecControlSecType
			INTEGER,
		netSecControlActOnIntr
			INTEGER,
		netSecControlClearAddrs
			INTEGER,
		netSecControlAutolearnMask
			INTEGER
		}

netSecControlSlotIndex OBJECT-TYPE
	SYNTAX INTEGER
	ACCESS read-only
	STATUS mandatory
	DESCRIPTION
		"The slot number index (used along with the port index)."
	::= { netSecControlEntry 1 }

netSecControlPortIndex OBJECT-TYPE
	SYNTAX INTEGER
	ACCESS read-only
	STATUS mandatory
	DESCRIPTION
		"The port number index (used along with the slot index)."
	::= { netSecControlEntry 2 }

netSecControlMode OBJECT-TYPE
	SYNTAX INTEGER {
		enable(1),
		disable(2)
		}
	ACCESS read-write
	STATUS mandatory
	DESCRIPTION
		"The desired security mode for this port.  Setting
		this object to enable(1) is equivalent to setting the
		'SecType' object (see below) to full(1), since both actions
		enable Eavesdropping and Intrusion Security."
	::= { netSecControlEntry 3 }

netSecControlSecType OBJECT-TYPE
	SYNTAX INTEGER {
		full(1),
		intrusion-only(2),
		eavesdropping-only(3),
		no-security(4)
		}
	ACCESS read-write
	STATUS mandatory
	DESCRIPTION
		"Setting this object enables a certain type of security
		for this port: Eavesdropping Security-only, Intrusion
		Security-only, or Full.  Note that setting this object to
		full(1) is equivalent to setting the 'Mode' object (see above)
		to enable(1)."
	::= { netSecControlEntry 4 }

netSecControlActOnIntr OBJECT-TYPE
	SYNTAX INTEGER {
		disable-and-trap(1),
		disable-only(2),
		trap-only(3),
		no-action(4)
		}
	ACCESS read-write
	STATUS mandatory
	DESCRIPTION
		"This object can be used to get or set the port_action_on_
		intrusion flag on a per-port basis.  When an Intrusion
		Security breach is attempted on a port, the Security Module
		can automatically disable the port and/or generate a trap to
		management, as dictated by this flag."
	::= { netSecControlEntry 5 }

netSecControlClearAddrs OBJECT-TYPE
	SYNTAX INTEGER {
		clear-all-addrs(1),
		not-clear(2)
		}
	ACCESS read-write
	STATUS mandatory
	DESCRIPTION
		"When this object is set to clear-all-addrs(1) then all of
		the security MAC addresses associated with this port
		will be cleared.  Note that this will not change the state
		of the 'Mode' (or any other) object in this table."
	::= { netSecControlEntry 6 }

netSecControlAutolearnMask OBJECT-TYPE
	SYNTAX INTEGER {
		enable(1),
		disable(2)
		}
	ACCESS read-write
	STATUS mandatory
	DESCRIPTION
		"This mask is used when autolearning is performed to determine
		whether the nMM should learn any security MAC addresses for
		this port.  If this object is set to enable(1) then the nMM
		will ignore this port during autolearning.  Note that
		autolearning is not supported by the TRMM."
	::= { netSecControlEntry 7 }


netSecAutolearn OBJECT IDENTIFIER ::= { netSec 3 }

netSecAutolearnTrigger OBJECT-TYPE
	SYNTAX INTEGER {
		autolearn(1),
		no-autolearn(2)
		}
	ACCESS read-write
	STATUS mandatory
	DESCRIPTION
		"When this object is set to autolearn(1) then the nMM
		will capture a snapshot of its MAC address cache for those
		ports whose 'AutolearnMask' object is disabled(2).
		This snapshot may be investigated and modified via the
		'LearnTable' (see below).  The snapshot of addresses may
		be downloaded to the Security Module via the 'Download'
		object (see below)."
	::= { netSecAutolearn 1 }

netSecAutolearnDownload OBJECT-TYPE
	SYNTAX INTEGER {
		download-addresses(1),
		no-download(2)
		}
	ACCESS read-write
	STATUS mandatory
	DESCRIPTION
		"When this object is set to download-addresses(1) then the
		nMM will download its snapshot of addresses to the Security
		Module."
	::= { netSecAutolearn 2 }


netSecLearnTable OBJECT-TYPE
	SYNTAX SEQUENCE OF NetSecLearnEntry
	ACCESS not-accessible
	STATUS mandatory
	DESCRIPTION
		"A table of security MAC addresses which have been autolearned
		on the nMM by taking a snapshot of its MAC address cache."
	::= { netSec 4 }

netSecLearnEntry OBJECT-TYPE
	SYNTAX NetSecLearnEntry
	ACCESS not-accessible
	STATUS mandatory
	DESCRIPTION
		"Security MAC addresses which have been autolearned (indexed
		by slot, port, and address)."
	INDEX { netSecLearnSlotIndex, netSecLearnPortIndex,
		netSecLearnAddress }
	::= { netSecLearnTable 1 }

NetSecLearnEntry ::=
	SEQUENCE {
		netSecLearnSlotIndex
			INTEGER,
		netSecLearnPortIndex
			INTEGER,
		netSecLearnAddress
			MacAddress,
		netSecLearnStatus
			INTEGER
		}

netSecLearnSlotIndex OBJECT-TYPE
	SYNTAX INTEGER
	ACCESS read-only
	STATUS mandatory
	DESCRIPTION
		"The slot number index (used along with the port and address
		indices)."
	::= { netSecLearnEntry 1 }

netSecLearnPortIndex OBJECT-TYPE
	SYNTAX INTEGER
	ACCESS read-only
	STATUS mandatory
	DESCRIPTION
		"The port number index (used along with the slot and address
		indices)."
	::= { netSecLearnEntry 2 }

netSecLearnAddress OBJECT-TYPE
	SYNTAX MacAddress
	ACCESS read-write
	STATUS mandatory
	DESCRIPTION
		"The security MAC address index (used along with the slot and
		port indices).  Note that there may be multiple addresses per
		port."
	::= { netSecLearnEntry 3 }

netSecLearnStatus OBJECT-TYPE
	SYNTAX INTEGER {
		valid(1),
		invalid(2)
		}
	ACCESS read-write
	STATUS mandatory
	DESCRIPTION
		"Setting this object to valid(1) will cause the
		corresponding security MAC address to be included in
		the snapshot of autolearned addresses.  Setting this
		object to invalid(2) will clear the corresponding MAC
		address from the snapshot of autolearned addresses."
	::= { netSecLearnEntry 4 }


netSecIntruderTable OBJECT-TYPE
	SYNTAX SEQUENCE OF NetSecIntruderEntry
	ACCESS not-accessible
	STATUS mandatory
	DESCRIPTION
		"A table of entries which describe Intrusion Security
		breach attempts.  This table contains the same info as
		the following table, the difference being that this table
		is indexed by time only and the other is indexed by slot.
		port.time."
	::= { netSec 5 }

netSecIntruderEntry OBJECT-TYPE
	SYNTAX NetSecIntruderEntry
	ACCESS not-accessible
	STATUS mandatory
	DESCRIPTION
		"A table of entries which describe Intrusion Security
		breach attempts.  The index is simply the chronological
		order in which the attempt occurred; e.g. index 1
		corresponds to the first intrusion attempt, index 2
		to the next one, and so on.  Note that the the oldest
		entry will be deleted automatically when a new entry is
		added to a full table."
	INDEX { netSecIntruderChronIndex }
	::= { netSecIntruderTable 1 }

NetSecIntruderEntry ::=
	SEQUENCE {
		netSecIntruderChronIndex
			INTEGER,
		netSecIntruderSlot
			INTEGER,
		netSecIntruderPort
			INTEGER,
		netSecIntruderAddress
			MacAddress,
		netSecIntruderTimeSince
			TimeTicks,
		netSecIntruderDisabled
			INTEGER
		}

netSecIntruderChronIndex OBJECT-TYPE
	SYNTAX INTEGER
	ACCESS read-only
	STATUS mandatory
	DESCRIPTION
		"The chronological index into the Intruder Table.  An index of
		1 corresponds to the first Intrusion Security breach attempt,
		an index of 2 corresponds to the next attempt, etc.  Note
		that the oldest entry will be deleted automatically when a
		new entry is added to a full table."
	::= { netSecIntruderEntry 1 }

netSecIntruderSlot OBJECT-TYPE
	SYNTAX INTEGER
	ACCESS read-only
	STATUS mandatory
	DESCRIPTION
		"The slot number on which the intrusion attempt occurred."
	::= { netSecIntruderEntry 2 }

netSecIntruderPort OBJECT-TYPE
	SYNTAX INTEGER
	ACCESS read-only
	STATUS mandatory
	DESCRIPTION
		"The port number on which the intrusion attempt occurred."
	::= { netSecIntruderEntry 3 }

netSecIntruderAddress OBJECT-TYPE
	SYNTAX MacAddress
	ACCESS read-only
	STATUS mandatory
	DESCRIPTION
		"The address of the intruder, if known.  If it is not known then
		this object will equal all zeroes."
	::= { netSecIntruderEntry 4 }

netSecIntruderTimeSince OBJECT-TYPE
	SYNTAX TimeTicks
	ACCESS read-only
	STATUS mandatory
	DESCRIPTION
		"The time in hundredths of a second since the Intrusion Security
		breach attempt took place.  For example, if it is equal to 500
		ticks then the intrusion attempt occurred 5 seconds ago."
	::= { netSecIntruderEntry 5 }

netSecIntruderDisabled OBJECT-TYPE
	SYNTAX INTEGER {
		auto-disabled(1),
		not-auto-disabled(2)
		}
	ACCESS read-only
	STATUS mandatory
	DESCRIPTION
		"This object indicates whether the port on which the intrusion
		attempt took place was automatically disabled."
	::= { netSecIntruderEntry 6 }


netSecPortIntrTable OBJECT-TYPE
	SYNTAX SEQUENCE OF NetSecPortIntrEntry
	ACCESS not-accessible
	STATUS mandatory
	DESCRIPTION
		"A table of entries which describe Intrusion Security
		breach attempts.  This table contains the same info as
		the previous table, the difference being the indices used
		to access the data."
	::= { netSec 6 }

netSecPortIntrEntry OBJECT-TYPE
	SYNTAX NetSecPortIntrEntry
	ACCESS not-accessible
	STATUS mandatory
	DESCRIPTION
		"A table of entries which describe Intrusion Security
		breach attempts.  The indices are the slot, port, and
		chronological order in time of the intrusion attempt."
	INDEX { netSecPortIntrSlotIndex, netSecPortIntrPortIndex,
		  netSecPortIntrChronIndex }
	::= { netSecPortIntrTable 1 }

NetSecPortIntrEntry ::=
	SEQUENCE {
		netSecPortIntrSlotIndex
			INTEGER,
		netSecPortIntrPortIndex
			INTEGER,
		netSecPortIntrChronIndex
			INTEGER,
		netSecPortIntrAddress
			MacAddress,
		netSecPortIntrTimeSince
			TimeTicks,
		netSecPortIntrDisabled
			INTEGER
		}

netSecPortIntrSlotIndex OBJECT-TYPE
	SYNTAX INTEGER
	ACCESS read-only
	STATUS mandatory
	DESCRIPTION
		"The slot number on which the intrusion attempt occurred."
	::= { netSecPortIntrEntry 1 }

netSecPortIntrPortIndex OBJECT-TYPE
	SYNTAX INTEGER
	ACCESS read-only
	STATUS mandatory
	DESCRIPTION
		"The port number on which the intrusion attempt occurred."
	::= { netSecPortIntrEntry 2 }

netSecPortIntrChronIndex OBJECT-TYPE
	SYNTAX INTEGER
	ACCESS read-only
	STATUS mandatory
	DESCRIPTION
		"The chronological index into the Intruder Table.  An index of
		1 corresponds to the first Intrusion Security breach attempt
		for that port, an index of 2 corresponds to the next attempt,
		etc.  Note that the oldest overall entry (regardless of slot
		and port) will be deleted automatically when a new entry is
		added to a full table."
	::= { netSecPortIntrEntry 3 }

netSecPortIntrAddress OBJECT-TYPE
	SYNTAX MacAddress
	ACCESS read-only
	STATUS mandatory
	DESCRIPTION
		"The address of the intruder, if known.  If it is not known then
		this object will equal all zeroes."
	::= { netSecPortIntrEntry 4 }

netSecPortIntrTimeSince OBJECT-TYPE
	SYNTAX TimeTicks
	ACCESS read-only
	STATUS mandatory
	DESCRIPTION
		"The time in hundredths of a second since the Intrusion Security
		breach attempt took place.  For example, if it is equal to 500
		ticks then the intrusion attempt occurred 5 seconds ago."
	::= { netSecPortIntrEntry 5 }

netSecPortIntrDisabled OBJECT-TYPE
	SYNTAX INTEGER {
		auto-disabled(1),
		not-auto-disabled(2)
		}
	ACCESS read-only
	STATUS mandatory
	DESCRIPTION
		"This object indicates whether the port on which the intrusion
		attempt took place was automatically disabled."
	::= { netSecPortIntrEntry 6 }


netSecTrap	OBJECT IDENTIFIER ::= { netSec 7 }

netSecTrapReason OBJECT-TYPE
	SYNTAX INTEGER {
		not-applicable(1),
		intrusion-attempt(2)
		}
	ACCESS read-only
	STATUS mandatory
	DESCRIPTION
		"This object is included in security traps to specify the
		reason for the trap.  When this object is read it will represent
		the reason for the most recently generated security trap.  If
		this object is read before any security traps have been generated
		then the value not-applicable(1) will be returned."
	::= { netSecTrap 1 }




-- The enet Group

-- This group represents information about Ethernet networks.

enetStatsTable OBJECT-TYPE
	SYNTAX SEQUENCE OF EnetStatsEntry
	ACCESS not-accessible
	STATUS mandatory
	DESCRIPTION
		"A table that contains statistical information about
		Ethernet (IEEE 802.3) networks."
	::= { enet 1 }

enetStatsEntry OBJECT-TYPE
	SYNTAX EnetStatsEntry
	ACCESS not-accessible
	STATUS mandatory
	DESCRIPTION
		"A list of statistical information about each Ethernet
		(IEEE 802.3) network in the concentrator."
	INDEX { enetStatsNetID }
	::= { enetStatsTable 1 }

EnetStatsEntry ::=
	SEQUENCE {
		enetStatsNetID
			INTEGER,
		enetStatsFramesRcvdOks
			Counter,
		enetStatsOctetsRcvdOks
			Counter,
		enetStatsMcastRcvdOks
			Counter,
		enetStatsBcastRcvdOks
			Counter,
		enetStatsFrameTooLongs
			Counter,
		enetStatsAlignmentErrors
			Counter,
		enetStatsFCSErrors
			Counter,
		enetStatsRunts
			Counter,
		enetStatsLocalColls
			Counter,
		enetStatsDropEvents
			Counter
		}

enetStatsNetID OBJECT-TYPE
	SYNTAX INTEGER {
		ethernet-1(6), -- corresponds to ifIndex
		ethernet-2(7),
		ethernet-3(8),
		ethernet-4(32),
		ethernet-5(33),
		ethernet-6(34),
		ethernet-7(35),
		ethernet-8(36)
		}
	ACCESS read-only
	STATUS mandatory
	DESCRIPTION
		"The network index that uniquely identifies this network."
	::= { enetStatsEntry 1 }

enetStatsFramesRcvdOks OBJECT-TYPE
	SYNTAX Counter
	ACCESS read-only
	STATUS mandatory
	DESCRIPTION
		"The count of frames that were successfully received by this
		network.  This counter does not include frames received
		in error."
	::= { enetStatsEntry 2 }

enetStatsOctetsRcvdOks OBJECT-TYPE
	SYNTAX Counter
	ACCESS read-only
	STATUS mandatory
	DESCRIPTION
		"The count of the number of octets that were successfully
		received by this network.  This counter does not include
		octets that were part of frames that were received in error."
	::= { enetStatsEntry 3 }

enetStatsMcastRcvdOks OBJECT-TYPE
	SYNTAX Counter
	ACCESS read-only
	STATUS mandatory
	DESCRIPTION
		"The count of the number of multicast frames successfully
		received by this network."
	::= { enetStatsEntry 4 }

enetStatsBcastRcvdOks OBJECT-TYPE
	SYNTAX Counter
	ACCESS read-only
	STATUS mandatory
	DESCRIPTION
		"The count of the number of broadcast frames successfully
		received by this network."
	::= { enetStatsEntry 5 }

enetStatsFrameTooLongs OBJECT-TYPE
	SYNTAX Counter
	ACCESS read-only
	STATUS mandatory
	DESCRIPTION
		"The count of the number of frames received by this network
		that exceeds the maximum permitted Ethernet (802.3) frame
		size."
	::= { enetStatsEntry 6 }

enetStatsAlignmentErrors OBJECT-TYPE
	SYNTAX Counter
	ACCESS read-only
	STATUS mandatory
	DESCRIPTION
		"The count of the number of frames received by this network
		that did not pass the frame check sequence (FCS) check
		and that are not an integral number of octets.  These
		frames are not counted in enetStatsFCSErrors."
	::= { enetStatsEntry 7 }

enetStatsFCSErrors OBJECT-TYPE
	SYNTAX Counter
	ACCESS read-only
	STATUS mandatory
	DESCRIPTION
		"The count of the number of frames received by this network
		that did not pass the frame check sequence (FCS) check
		and are an integral number of octets."
	::= { enetStatsEntry 8 }

enetStatsRunts OBJECT-TYPE
	SYNTAX Counter
	ACCESS read-only
	STATUS mandatory
	DESCRIPTION
		"The count of the number of frames received by this network
		 that are less than 512 bits long.  "
	::= { enetStatsEntry 9 }

enetStatsLocalColls OBJECT-TYPE
	SYNTAX Counter
	ACCESS read-only
	STATUS mandatory
	DESCRIPTION
		"The count of the number of times that two or more ports
		within this concentrator have received traffic simultaneously."
	::= { enetStatsEntry 10 }

enetStatsDropEvents OBJECT-TYPE
	SYNTAX Counter
	ACCESS read-only
	STATUS mandatory
	DESCRIPTION
		"The total number of events in which frames were dropped
		due to lack of resources.  Note that this number is not
		necessarily the number of frames dropped; it is just
		the number of times this condition has been detected."
	::= { enetStatsEntry 11 }


enetStatsModTable OBJECT-TYPE
	SYNTAX SEQUENCE OF EnetStatsModEntry
	ACCESS not-accessible
	STATUS mandatory
	DESCRIPTION
		"A table of statistical information counted for each module
		in each Ethernet (IEEE 802.3) network."
	::= { enet 2 }

enetStatsModEntry OBJECT-TYPE
	SYNTAX EnetStatsModEntry
	ACCESS not-accessible
	STATUS mandatory
	DESCRIPTION
		"A list of statistical information for each port
		on each Ethernet (IEEE 802.3) network in the concentrator."
	INDEX { enetStatsModNetID, enetStatsModSlotIndex }
	::= { enetStatsModTable 1 }

EnetStatsModEntry ::=
	SEQUENCE {
		enetStatsModNetID
			INTEGER,
		enetStatsModSlotIndex
			INTEGER,
		enetStatsModFramesRcvdOks
			Counter,
		enetStatsModOctetsRcvdOks
			Counter,
		enetStatsModMcastRcvdOks
			Counter,
		enetStatsModBcastRcvdOks
			Counter,
		enetStatsModFrameTooLongs
			Counter,
		enetStatsModAlignmentErrors
			Counter,
		enetStatsModFCSErrors
			Counter,
		enetStatsModRunts
			Counter
		}

enetStatsModNetID OBJECT-TYPE
	SYNTAX INTEGER {
		ethernet-1(6), -- corresponds to ifIndex
		ethernet-2(7),
		ethernet-3(8)
		}
	ACCESS read-only
	STATUS mandatory
	DESCRIPTION
		"The unique identifier for this network."
	::= { enetStatsModEntry 1 }

enetStatsModSlotIndex OBJECT-TYPE
	SYNTAX INTEGER
	ACCESS read-only
	STATUS mandatory
	DESCRIPTION
		"The slot number that contains this module."
	::= { enetStatsModEntry 2 }

enetStatsModFramesRcvdOks OBJECT-TYPE
	SYNTAX Counter
	ACCESS read-only
	STATUS mandatory
	DESCRIPTION
		"The count of frames that were successfully received by this
		module.  This counter does not include frames received in
		error."
	::= { enetStatsModEntry 3 }

enetStatsModOctetsRcvdOks OBJECT-TYPE
	SYNTAX Counter
	ACCESS read-only
	STATUS mandatory
	DESCRIPTION
		"The count of the number of octets that were successfully
		received by this module.  This counter does not include
		octets that were part of frames that were received in error."
	::= { enetStatsModEntry 4 }

enetStatsModMcastRcvdOks OBJECT-TYPE
	SYNTAX Counter
	ACCESS read-only
	STATUS mandatory
	DESCRIPTION
		"The count of the number of multicast frames successfully
		received by this module."
	::= { enetStatsModEntry 5 }

enetStatsModBcastRcvdOks OBJECT-TYPE
	SYNTAX Counter
	ACCESS read-only
	STATUS mandatory
	DESCRIPTION
		"The count of the number of broadcast frames successfully
		received by this module."
	::= { enetStatsModEntry 6 }

enetStatsModFrameTooLongs OBJECT-TYPE
	SYNTAX Counter
	ACCESS read-only
	STATUS mandatory
	DESCRIPTION
		"The count of the number of frames received by this module
		that exceeds the maximum permitted Ethernet (802.3) frame
		size."
	::= { enetStatsModEntry 7 }

enetStatsModAlignmentErrors OBJECT-TYPE
	SYNTAX Counter
	ACCESS read-only
	STATUS mandatory
	DESCRIPTION
		"The count of the number of frames received by this module
		that did not pass the frame check sequence (FCS) check
		and that are not an integral number of octets.  These
		frames are not counted in enetStatsModFCSErrors."
	::= { enetStatsModEntry 8 }

enetStatsModFCSErrors OBJECT-TYPE
	SYNTAX Counter
	ACCESS read-only
	STATUS mandatory
	DESCRIPTION
		"The count of the number of frames received by this module
		that did not pass the frame check sequence (FCS) check
		and are an integral number of octets."
	::= { enetStatsModEntry 9 }

enetStatsModRunts OBJECT-TYPE
	SYNTAX Counter
	ACCESS read-only
	STATUS mandatory
	DESCRIPTION
		"The count of the number of frames received by
		this module that are less than 512 bits long.  "
	::= { enetStatsModEntry 10 }


enetStatsPortTable OBJECT-TYPE
	SYNTAX SEQUENCE OF EnetStatsPortEntry
	ACCESS not-accessible
	STATUS mandatory
	DESCRIPTION
		"A table of statistical information counted for each port
		in each Ethernet (IEEE 802.3) network."
	::= { enet 3 }

enetStatsPortEntry OBJECT-TYPE
	SYNTAX EnetStatsPortEntry
	ACCESS not-accessible
	STATUS mandatory
	DESCRIPTION
		"A list of statistical information for each port
		on each Ethernet (IEEE 802.3) network in the concentrator."
	INDEX { enetStatsPortSlotIndex, enetStatsPortIndex }
	::= { enetStatsPortTable 1 }

EnetStatsPortEntry ::=
	SEQUENCE {
		enetStatsPortNetID
			INTEGER,
		enetStatsPortSlotIndex
			INTEGER,
		enetStatsPortIndex
			INTEGER,
		enetStatsPortFramesRcvdOks
			Counter,
		enetStatsPortOctetsRcvdOks
			Counter,
		enetStatsPortMcastRcvdOks
			 Counter,
		 enetStatsPortBcastRcvdOks
			 Counter,
		 enetStatsPortFrameTooLongs
			 Counter,
		 enetStatsPortAlignmentErrors
			 Counter,
		 enetStatsPortFCSErrors
			 Counter,
		 enetStatsPortRunts
			 Counter,
		 enetStatsPortSrcAddrChanges
			 Counter,
		 enetStatsPortLastSrcAddr
			 OCTET STRING (SIZE(6)),
		 enetStatsPortLastErrAddr
			 OCTET STRING (SIZE(6))
		 }

enetStatsPortNetID OBJECT-TYPE
	 SYNTAX INTEGER {
		 ethernet-1(6), -- corresponds to ifIndex
		 ethernet-2(7),
		 ethernet-3(8),
		 ethernet-4(32),
		 ethernet-5(33),
		 ethernet-6(34),
		 ethernet-7(35),
		 ethernet-8(36)
		 }
	 ACCESS read-only
	 STATUS mandatory
	 DESCRIPTION
		 "The unique identifier for this network."
	 ::= { enetStatsPortEntry 1 }

enetStatsPortSlotIndex OBJECT-TYPE
	 SYNTAX INTEGER
	 ACCESS read-only
	 STATUS mandatory
	 DESCRIPTION
		 "The slot number that contains this port."
	 ::= { enetStatsPortEntry 2 }

enetStatsPortIndex OBJECT-TYPE
	 SYNTAX INTEGER
	 ACCESS read-only
	 STATUS mandatory
	 DESCRIPTION
		 "The port number within this slot."
	 ::= { enetStatsPortEntry 3 }

enetStatsPortFramesRcvdOks OBJECT-TYPE
	 SYNTAX Counter
	 ACCESS read-only
	 STATUS mandatory
	 DESCRIPTION
		 "The count of frames that were successfully received by this
		 port.  This counter does not include frames received in error."
	 ::= { enetStatsPortEntry 4 }

enetStatsPortOctetsRcvdOks OBJECT-TYPE
	 SYNTAX Counter
	 ACCESS read-only
	 STATUS mandatory
	 DESCRIPTION
		 "The count of the number of octets that were successfully
		 received by this port.  This counter does not include
		 octets that were part of frames that were received in error."
	 ::= { enetStatsPortEntry 5 }

enetStatsPortMcastRcvdOks OBJECT-TYPE
	 SYNTAX Counter
	 ACCESS read-only
	 STATUS mandatory
	 DESCRIPTION
		 "The count of the number of multicast frames successfully
		 received by this port."
	 ::= { enetStatsPortEntry 6 }

enetStatsPortBcastRcvdOks OBJECT-TYPE
	 SYNTAX Counter
	 ACCESS read-only
	 STATUS mandatory
	 DESCRIPTION
		 "The count of the number of broadcast frames successfully
		 received by this port."
	 ::= { enetStatsPortEntry 7 }

enetStatsPortFrameTooLongs OBJECT-TYPE
	 SYNTAX Counter
	 ACCESS read-only
	 STATUS mandatory
	 DESCRIPTION
		 "The count of the number of frames received by this port
		 that exceeds the maximum permitted Ethernet (802.3) frame
		 size."
	 ::= { enetStatsPortEntry 8 }

enetStatsPortAlignmentErrors OBJECT-TYPE
	 SYNTAX Counter
	 ACCESS read-only
	 STATUS mandatory
	 DESCRIPTION
		 "The count of the number of frames received by this port
		 that did not pass the frame check sequence (FCS) check
		 and that are not an integral number of octets.  These
		 frames are not counted in enetStatsPortFCSErrors."
	 ::= { enetStatsPortEntry 9 }

enetStatsPortFCSErrors OBJECT-TYPE
	 SYNTAX Counter
	 ACCESS read-only
	 STATUS mandatory
	 DESCRIPTION
		 "The count of the number of frames received by this port
		 that did not pass the frame check sequence (FCS) check
		 and are an integral number of octets."
	 ::= { enetStatsPortEntry 10 }

enetStatsPortRunts OBJECT-TYPE
	 SYNTAX Counter
	 ACCESS read-only
	 STATUS mandatory
	 DESCRIPTION
		 "The count of the number of frames received by this port that
		 are less than 512 bits long.  "
	 ::= { enetStatsPortEntry 11 }


enetStatsPortSrcAddrChanges OBJECT-TYPE
	 SYNTAX Counter
	 ACCESS read-only
	 STATUS mandatory
	 DESCRIPTION
		 "The count of the number of times that
		 enetStatsPortLastSourceAddr
		{ enetStatsPortEntry 11 } has changed."
	 ::= { enetStatsPortEntry 12 }

enetStatsPortLastSrcAddr OBJECT-TYPE
	 SYNTAX OCTET STRING (SIZE(6))
	 ACCESS read-only
	 STATUS mandatory
	 DESCRIPTION
		 "The last source address seen on this port for this
		 network for the last successfully received frame."
	 ::= { enetStatsPortEntry 13 }

enetStatsPortLastErrAddr OBJECT-TYPE
	 SYNTAX OCTET STRING (SIZE(6))
	 ACCESS read-only
	 STATUS mandatory
	 DESCRIPTION
		 "The value stored in the source address portion of
		 a frame received in error (alignment, FCS, or too long).
		 Since the frame was received in error, there is no
		 guarantee that this is an actual valid address."
	 ::= { enetStatsPortEntry 14 }

enetMapTable OBJECT-TYPE
	 SYNTAX SEQUENCE OF EnetMapEntry
	 ACCESS not-accessible
	 STATUS mandatory
	 DESCRIPTION
		 "A table that contains a cache of information relating
		 an Ethernet source address with a specific port for
		 a given network.  An indication of this source's utilization
		 of the network is also provided."
	 ::= { enet 4 }

enetMapEntry OBJECT-TYPE
	 SYNTAX EnetMapEntry
	 ACCESS not-accessible
	 STATUS mandatory
	 DESCRIPTION
		 "A list of information that tracks a source address to
		 a specific port for each network."
	 INDEX { enetMapNetID, enetMapAddress }
	 ::= { enetMapTable 1 }

EnetMapEntry ::=
	 SEQUENCE {
		 enetMapNetID
			 INTEGER,
		 enetMapAddress
			 OCTET STRING,
		 enetMapSlotIndex
			 INTEGER,
		 enetMapPortIndex
			 INTEGER,
		 enetMapFrames
			 Counter,
		 enetMapOctets
			 Counter,
		 enetMapTime
			 TimeTicks
		 }

enetMapNetID OBJECT-TYPE
	 SYNTAX INTEGER {
		 ethernet-1(6),  -- corresponds to ifIndex
		 ethernet-2(7),
		 ethernet-3(8),
		 ethernet-4(32),
		 ethernet-5(33),
		 ethernet-6(34),
		 ethernet-7(35),
		 ethernet-8(36)
		 }
	 ACCESS read-only
	 STATUS mandatory
	 DESCRIPTION
		 "The network index that uniquely identifies this network."
	 ::= { enetMapEntry 1 }

enetMapAddress OBJECT-TYPE
	 SYNTAX OCTET STRING (SIZE(6))
	 ACCESS read-only
	 STATUS mandatory
	 DESCRIPTION
		 "An Ethernet source address received by this port on this
		 network."
	 ::= { enetMapEntry 2 }

enetMapSlotIndex OBJECT-TYPE
	 SYNTAX INTEGER
	 ACCESS read-only
	 STATUS mandatory
	 DESCRIPTION
		 "The slot number of the port that received this address."
	 ::= { enetMapEntry 3 }


enetMapPortIndex OBJECT-TYPE
	 SYNTAX INTEGER
	 ACCESS read-only
	 STATUS mandatory
	 DESCRIPTION
		 "The port number within enetMapSlotIndex's slot that
		 received this address."
	 ::= { enetMapEntry 4 }

enetMapFrames OBJECT-TYPE
	 SYNTAX Counter
	 ACCESS read-only
	 STATUS mandatory
	 DESCRIPTION
		 "An estimated count of the number of frames generated by this
		 address.  This count should be interpreted as an
		 indicator, not a true frame count."
	 ::= { enetMapEntry 5 }

enetMapOctets OBJECT-TYPE
	 SYNTAX Counter
	 ACCESS read-only
	 STATUS mandatory
	 DESCRIPTION
		 "An estimated count of the number of octets generated by this
		 address.  This count should be interpreted as an
		 indicator, not a true octet count."
	 ::= { enetMapEntry 6 }

enetMapTime OBJECT-TYPE
	 SYNTAX TimeTicks
	 ACCESS read-only
	 STATUS mandatory
	 DESCRIPTION
		 "The time in in hundredths of a second since this address
		 was last seen.  For example, if enetMapTime is 500
		 ticks, then this adddress was seen 5 seconds ago."
	 ::= { enetMapEntry 7 }


ocSnmpDot3RptrMgt OBJECT IDENTIFIER ::= { enet 5 }




--			References
--
-- The following references are used throughout this MIB:
--
-- [IEEE 802.3 Std]
--    refers to IEEE 802.3/ISO 8802-3 Information processing
--    systems - Local area networks - Part 3: Carrier sense
--    multiple access with collision detection (CSMA/CD)
--    access method and physical layer specifications
--    (2nd edition, September 21, 1990).
--
-- [IEEE 802.3 Rptr Mgt]
--    refers to IEEE P802.3K, 'Layer Management for 10 Mb/s
--    Baseband Repeaters, Section 19,' Draft Supplement to
--    ANSI/IEEE 802.3, (Draft 8, April 9, 1992)


--			MIB Groups
--
-- The rptrBasicPackage group is mandatory.
-- The rptrMonitorPackage and rptrAddrTrackPackage
-- groups are optional.


ocRptrBasicPackage  OBJECT IDENTIFIER ::= { ocSnmpDot3RptrMgt 1 }

ocRptrMonitorPackage OBJECT IDENTIFIER ::= { ocSnmpDot3RptrMgt 2 }

ocRptrAddrTrackPackage OBJECT IDENTIFIER ::= { ocSnmpDot3RptrMgt 3 }


-- object identifiers for organizing the information
-- in the groups by repeater, port-group, and port

ocRptrRptrInfo OBJECT IDENTIFIER ::= { ocRptrBasicPackage 1 }
ocRptrGroupInfo OBJECT IDENTIFIER ::= { ocRptrBasicPackage 2 }
ocRptrPortInfo OBJECT IDENTIFIER ::= { ocRptrBasicPackage 3 }

ocRptrMonitorRptrInfo OBJECT IDENTIFIER ::= { ocRptrMonitorPackage 1 }
ocRptrMonitorGroupInfo OBJECT IDENTIFIER ::= { ocRptrMonitorPackage 2 }

ocRptrMonitorPortInfo OBJECT IDENTIFIER ::= { ocRptrMonitorPackage 3 }

-- this subtree is currently unused
ocRptrAddrTrackRptrInfo  OBJECT IDENTIFIER ::= { ocRptrAddrTrackPackage 1 }

-- this subtree is currently unused
ocRptrAddrTrackGroupInfo OBJECT IDENTIFIER ::= { ocRptrAddrTrackPackage 2 }
ocRptrAddrTrackPortInfo OBJECT IDENTIFIER ::= { ocRptrAddrTrackPackage 3 }

--
--		      The BASIC GROUP
--
-- Implementation of the Basic Group is mandatory for all
-- managed repeaters.


--
-- Basic Repeater Information
--
-- Configuration, status, and control objects for the overall
-- repeater
--
ocRptrRptrInfoTable OBJECT-TYPE
       SYNTAX	 SEQUENCE OF OcRptrRptrInfoEntry
       ACCESS	 not-accessible
       STATUS	 mandatory
       DESCRIPTION
	       "Table of descriptive and status information about
	       the repeater."
       ::= { ocRptrRptrInfo 1 }

ocRptrRptrInfoEntry OBJECT-TYPE
       SYNTAX	 OcRptrRptrInfoEntry
       ACCESS	 not-accessible
       STATUS	 mandatory
       DESCRIPTION
	       "An entry in the table, containing information
	       about a repeater."
       INDEX	{ ocRptrRptrInfoSlotIndex, ocRptrRptrInfoNetID }
       ::= { ocRptrRptrInfoTable 1 }

OcRptrRptrInfoEntry ::=
       SEQUENCE {
	  ocRptrRptrInfoSlotIndex
	       INTEGER,
	   ocRptrRptrInfoNetID
	       INTEGER,
	   ocRptrGroupCapacity
	       INTEGER,
	   ocRptrOperStatus
	       INTEGER,
	   ocRptrHealthText
	       DisplayString,
	   ocRptrReset
	       INTEGER,
	   ocRptrNonDisruptTest
	       INTEGER,
	   ocRptrTotalPartitionedPorts
	       Gauge
       }


ocRptrRptrInfoSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrRptrInfoNetID
		resides. If ocRptrRptrInfoNetID does not identify
		an isolated network, then the value of this object is
		backplane(255)."
	::= {ocRptrRptrInfoEntry  1 }

ocRptrRptrInfoNetID OBJECT-TYPE
	 SYNTAX INTEGER {

		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this repeater."
       ::= { ocRptrRptrInfoEntry 2 }

ocRptrGroupCapacity OBJECT-TYPE
       SYNTAX	 INTEGER (1..1024)
       ACCESS	 read-only
       STATUS	 mandatory
       DESCRIPTION
		      "The ocRptrGroupCapacity is the number of groups
		      that can be contained within the repeater.  Within
		      each managed repeater, the groups are uniquely
		      numbered in the range from 1 to ocRptrGroupCapacity.

		      Some groups may not be present in the repeater, in
		      which case the actual number of groups present
		      will be less than ocRptrGroupCapacity.  The number
		      of groups present will never be greater than
		      ocRptrGroupCapacity.

		      Note:  In practice, this will generally be the
		      number of field-replaceable units (i.e., modules,
		      cards, or boards) that can fit in the physical
		      repeater enclosure, and the group numbers will
		      correspond to numbers marked on the physical
		      enclosure."
   REFERENCE
	       "Reference IEEE 802.3 Rptr Mgt, 19.2.3.2,
	       aRepeaterGroupCapacity."

   ::= { ocRptrRptrInfoEntry 3 }

ocRptrOperStatus OBJECT-TYPE
       SYNTAX  INTEGER {
		   other(1),		-- undefined or unknown status
		   ok(2),		-- no known failures
		   rptrFailure(3),	-- repeater-related failure
		   groupFailure(4),	-- group-related failure
		   portFailure(5),	-- port-related failure
		   generalFailure(6)	-- failure, unspecified type
	       }
       ACCESS	 read-only
       STATUS	 mandatory
       DESCRIPTION
	      "The ocRptrOperStatus object indicates the
	      operational state of the repeater.  The
	      ocRptrHealthText object may be consulted for more
	      specific information about the state of the
	      repeater's health.

	      In the case of multiple kinds of failures (e.g.,
	      repeater failure and port failure), the value of
	      this attribute shall reflect the highest priority
	      failure in the following order:

		   ocRptrFailure(3)
		   groupFailure(4)
		   portFailure(5)
		   generalFailure(6)."
       REFERENCE
	       "Reference IEEE 802.3 Rptr Mgt, 19.2.3.2,
	       aRepeaterHealthState."
       ::= { ocRptrRptrInfoEntry 4 }

ocRptrHealthText OBJECT-TYPE
       SYNTAX	 DisplayString (SIZE (0..255))
       ACCESS	 read-only
       STATUS	 mandatory
       DESCRIPTION
	       "The health text object is a text string that
	       provides information relevant to the operational
	       state of the repeater. Agents may use this string
	       to provide detailed information on current
	       failures, including how they were detected, and/or
	       instructions for problem resolution. The contents
	       are agent-specific."
       REFERENCE
	       "Reference IEEE 802.3 Rptr Mgt, 19.2.3.2,
	       aRepeaterHealthText."
       ::= { ocRptrRptrInfoEntry 5 }

ocRptrReset OBJECT-TYPE
       SYNTAX	 INTEGER {
		     noReset(1),
		     reset(2)
		 }
       ACCESS	 read-write
       STATUS	 mandatory
       DESCRIPTION
	       "Setting this object to reset(2) causes a
	       transition to the START state of Fig 9-2 in
	       section 9 [IEEE 802.3 Std].

	       Setting this object to noReset(1) has no effect.
	       The agent will always return the value noReset(1)
	       when this object is read.

	       This action does not reset the management counters
	       defined in this document nor does it affect the
	       portAdminStatus parameters.  Included in this
	       action is the execution of a disruptive Self-Test
	       with the following characteristics:  a) The nature
	       of the tests is not specified.  b) The test resets
	       the repeater but without affecting management
	       information about the repeater.  c) The test does
	       not inject packets onto any segment.  d) Packets
	       received during the test may or may not be
	       transferred.  e) The test does not interfere with
	       management functions.

	       As a result of this action a ocRptrResetEvent trap
	       should be sent."
       REFERENCE
	       "Reference IEEE 802.3 Rptr Mgt, 19.2.3.3,
	       acResetRepeater."
       ::= { ocRptrRptrInfoEntry 6 }

ocRptrNonDisruptTest OBJECT-TYPE
       SYNTAX	 INTEGER {
		     noSelfTest(1),
		     selfTest(2)
		 }
       ACCESS	 read-write
       STATUS	 mandatory
       DESCRIPTION
	       "Setting this object to selfTest(2) causes the

	       repeater to perform a agent-specific, non-
	       disruptive self-test that has the following
	       characteristics:  a) The nature of the tests is
	       not specified.  b) The test does not change the
	       state of the repeater or management information
	       about the repeater.  c) The test does not inject
	       packets onto any segment.  d) The test does not
	       prevent the relay of any packets.  e) The test
	       does not interfere with management functions.

	       After performing this test the agent will update
	       the repeater health information and send a
	       ocRptrHealth trap.

	       Setting this object to noSelfTest(1) has no
	       effect.  The agent will always return the value
	       noSelfTest(1) when this object is read."
       REFERENCE
	       "Reference IEEE 802.3 Rptr Mgt, 19.2.3.3,
	       acExecuteNonDisruptiveSelfTest."
       ::= { ocRptrRptrInfoEntry 7 }

ocRptrTotalPartitionedPorts OBJECT-TYPE
       SYNTAX	 Gauge
       ACCESS	 read-only
       STATUS	 mandatory
       DESCRIPTION
	       "This object returns the total number of ports in
	       the repeater whose current state meets all three
	       of the following criteria:  ocRptrPortOperStatus
	       does not have the value notPresent(3),
	       ocRptrPortAdminStatus is enabled(1), and
	       ocRptrPortAutoPartitionState is autoPartitioned(2)."
       ::= { ocRptrRptrInfoEntry 8 }

--
-- The Basic Port Group Table
--

ocRptrGroupTable OBJECT-TYPE
       SYNTAX	 SEQUENCE OF OcRptrGroupEntry
       ACCESS	 not-accessible
       STATUS	 mandatory
       DESCRIPTION
	       "Table of descriptive and status information about
	       the groups of ports."
       ::= { ocRptrGroupInfo 1 }

ocRptrGroupEntry OBJECT-TYPE
       SYNTAX	 OcRptrGroupEntry
       ACCESS	 not-accessible
       STATUS	 mandatory
       DESCRIPTION
	       "An entry in the table, containing information
	       about a single group of ports."
       INDEX	{ ocRptrGroupSlotIndex, ocRptrGroupNetID, ocRptrGroupIndex }
       ::= { ocRptrGroupTable 1 }

OcRptrGroupEntry ::=
       SEQUENCE {
	   ocRptrGroupSlotIndex
	       INTEGER,
	   ocRptrGroupNetID
	       INTEGER,
	   ocRptrGroupIndex
	       INTEGER,
	   ocRptrGroupDescr
	       DisplayString,
	   ocRptrGroupObjectID
	       OBJECT IDENTIFIER,
	   ocRptrGroupOperStatus
	       INTEGER,
	   ocRptrGroupLastOperStatusChange
	       TimeTicks,
	   ocRptrGroupPortCapacity
	       INTEGER
       }


ocRptrGroupSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrGroupNetID
		resides. If ocRptrGroupNetID does not identify
		an isolated network, then the value of this object is
		backplane(255)."
	::= {ocRptrGroupEntry 1 }

ocRptrGroupNetID OBJECT-TYPE
	 SYNTAX INTEGER {

		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this group's repeater."
       ::= { ocRptrGroupEntry 2 }

ocRptrGroupIndex OBJECT-TYPE
       SYNTAX	 INTEGER (1..1024)
       ACCESS	 read-only
       STATUS	 mandatory
       DESCRIPTION
	       "This object identifies the group within the
	       repeater for which this entry contains
	       information.  This value is never greater than
	       ocRptrGroupCapacity."
       REFERENCE
	       "Reference IEEE 802.3 Rptr Mgt, 19.2.5.2,
	       aGroupID."
       ::= { ocRptrGroupEntry 3 }

ocRptrGroupDescr OBJECT-TYPE
       SYNTAX	 DisplayString (SIZE (0..255))
       ACCESS	 read-only
       STATUS	 mandatory
       DESCRIPTION
	       "A textual description of the group.  This value
	       should include the full name and version
	       identification of the group's hardware type and

	       indicate how the group is differentiated from
	       other groups in the repeater.  Plug-in Module, Rev
	       A' or 'Barney Rubble 10BASE-T 4-port SIMM socket
	       Version 2.1' are examples of valid group
	       descriptions.

	       It is mandatory that this only contain printable
	       ASCII characters."
       ::= { ocRptrGroupEntry 4 }

ocRptrGroupObjectID OBJECT-TYPE
       SYNTAX	 OBJECT IDENTIFIER
       ACCESS	 read-only
       STATUS	 mandatory
       DESCRIPTION
	       "The vendor's authoritative identification of the
	       group.  This value is allocated within the SMI
	       enterprises subtree (1.3.6.1.4.1) and provides a
	       straight-forward and unambiguous means for
	       determining what kind of group is being managed.

	       For example, this object could take the value
	       1.3.6.1.4.1.4242.1.2.14 if vendor 'Flintstones,
	       Inc.' was assigned the subtree 1.3.6.1.4.1.4242,
	       and had assigned the identifier
	       1.3.6.1.4.1.4242.1.2.14 to its 'Wilma Flintstone
	       6-Port FOIRL Plug-in Module.'"
       ::= { ocRptrGroupEntry 5 }

ocRptrGroupOperStatus OBJECT-TYPE
       SYNTAX	 INTEGER {
		     other(1),
		     operational(2),
		     malfunctioning(3),
		     notPresent(4),
		     underTest(5),
		     resetInProgress(6)
		 }
       ACCESS	 read-only
       STATUS	 mandatory
       DESCRIPTION
	       "An object that indicates the operational status
	       of the group.

	       A status of notPresent(4) indicates that the group
	       is temporarily or permanently physically and/or
	       logically not a part of the repeater.  It is an
	       implementation-specific matter as to whether the

	       agent effectively removes notPresent entries from
	       the table.

	       A status of operational(2) indicates that the
	       group is functioning, and a status of
	       malfunctioning(3) indicates that the group is
	       malfunctioning in some way."
       ::= { ocRptrGroupEntry 6 }

ocRptrGroupLastOperStatusChange OBJECT-TYPE
       SYNTAX	 TimeTicks
       ACCESS	 read-only
       STATUS	 mandatory
       DESCRIPTION
	       "An object that contains the value of sysUpTime at
	       the time that the value of the ocRptrGroupOperStatus
	       object for this group last changed.

	       A value of zero indicates that the group's oper
	       status has not changed since the agent last
	       restarted."
       ::= { ocRptrGroupEntry 7 }

ocRptrGroupPortCapacity OBJECT-TYPE
       SYNTAX	 INTEGER (1..1024)
       ACCESS	 read-only
       STATUS	 mandatory
       DESCRIPTION
	       "The ocRptrGroupPortCapacity is the number of ports
	       that can be contained within the group.  Valid
	       range is 1-1024.  Within each group, the ports are
	       uniquely numbered in the range from 1 to
	       ocRptrGroupPortCapacity.

	       Note:  In practice, this will generally be the
	       number of ports on a module, card, or board, and
	       the port numbers will correspond to numbers marked
	       on the physical embodiment."
       REFERENCE
	       "Reference IEEE 802.3 Rptr Mgt, 19.2.5.2,
	       aGroupPortCapacity."
       ::= { ocRptrGroupEntry 8 }



--
-- The Basic Port Table
--

ocRptrPortTable OBJECT-TYPE
       SYNTAX	 SEQUENCE OF OcRptrPortEntry
       ACCESS	 not-accessible
       STATUS	 mandatory
       DESCRIPTION
	       "Table of descriptive and status information about
	       the ports."
       ::= { ocRptrPortInfo 1 }

ocRptrPortEntry OBJECT-TYPE
       SYNTAX	 OcRptrPortEntry
       ACCESS	 not-accessible
       STATUS	 mandatory
       DESCRIPTION
	       "An entry in the table, containing information
	       about a single port."
       INDEX	{ ocRptrPortSlotIndex, ocRptrPortNetID, ocRptrPortGroupIndex, ocRptrPortIndex }
       ::= { ocRptrPortTable 1 }

OcRptrPortEntry ::=
       SEQUENCE {
	   ocRptrPortSlotIndex
	       INTEGER,
	   ocRptrPortNetID
	       INTEGER,
	   ocRptrPortGroupIndex
	       INTEGER,
	   ocRptrPortIndex
	       INTEGER,
	   ocRptrPortAdminStatus
	       INTEGER,
	   ocRptrPortAutoPartitionState
	       INTEGER,
	   ocRptrPortOperStatus
	       INTEGER
       }


ocRptrPortSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrPortNetID
		resides. If ocRptrPortNetID does not identify
		an isolated network, then the value of this object is
		backplane(255)."
	::= {ocRptrPortEntry 1 }

ocRptrPortNetID OBJECT-TYPE
	 SYNTAX INTEGER {

		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this port's repeater."
       ::= { ocRptrPortEntry 2 }

ocRptrPortGroupIndex OBJECT-TYPE
       SYNTAX	 INTEGER (1..1024)
       ACCESS	 read-only
       STATUS	 mandatory
       DESCRIPTION
	       "This object identifies the group containing the
	       port for which this entry contains information."
       ::= { ocRptrPortEntry 3 }

ocRptrPortIndex OBJECT-TYPE
       SYNTAX	 INTEGER (1..1024)

       ACCESS	 read-only
       STATUS	 mandatory
       DESCRIPTION
	       "This object identifies the port within the group
	       for which this entry contains information.  This
	       value can never be greater than
	       ocRptrGroupPortCapacity for the associated group."
       REFERENCE
	       "Reference IEEE 802.3 Rptr Mgt, 19.2.6.2,
	       aPortID."
       ::= { ocRptrPortEntry 4 }

ocRptrPortAdminStatus OBJECT-TYPE
       SYNTAX	 INTEGER {
		     enabled(1),
		     disabled(2)
		 }
       ACCESS	 read-write
       STATUS	 mandatory
       DESCRIPTION
	       "Setting this object to disabled(2) disables the
	       port.  A disabled port neither transmits nor
	       receives.  Once disabled, a port must be
	       explicitly enabled to restore operation.  A port
	       which is disabled when power is lost or when a
	       reset is exerted shall remain disabled when normal
	       operation resumes.

	       The admin status takes precedence over auto-
	       partition and functionally operates between the
	       auto-partition mechanism and the AUI/PMA.

	       Setting this object to enabled(1) enables the port
	       and exerts a BEGIN on the port's auto-partition
	       state machine.
	       (In effect, when a port is disabled, the value of
	       ocRptrPortAutoPartitionState for that port is frozen
	       until the port is next enabled.  When the port
	       becomes enabled, the ocRptrPortAutoPartitionState
	       becomes notAutoPartitioned(1), regardless of its
	       pre-disabling state.)"
       REFERENCE
	       "Reference IEEE 802.3 Rptr Mgt, 19.2.6.2,
	       aPortAdminState and 19.2.6.3, acPortAdminControl."
       ::= { ocRptrPortEntry 5 }

ocRptrPortAutoPartitionState OBJECT-TYPE
       SYNTAX	 INTEGER {

		     notAutoPartitioned(1),
		     autoPartitioned(2)
		 }
       ACCESS	 read-only
       STATUS	 mandatory
       DESCRIPTION
	       "The autoPartitionState flag indicates whether the
	       port is currently partitioned by the repeater's
	       auto-partition protection.

	       The conditions that cause port partitioning are
	       specified in partition state machine in Section 9
	       [IEEE 802.3 Std].  They are not differentiated
	       here."
       REFERENCE
	       "Reference IEEE 802.3 Rptr Mgt, 19.2.6.2,
	       aAutoPartitionState."
       ::= { ocRptrPortEntry 6 }

ocRptrPortOperStatus  OBJECT-TYPE
       SYNTAX	 INTEGER {
		     operational(1),
		     notOperational(2),
		     notPresent(3)
		 }
       ACCESS	 read-only
       STATUS	 mandatory
       DESCRIPTION
	       "This object indicates the port's operational
	       status.  The notPresent(3) status indicates the
	       port is physically removed (note this may or may
	       not be possible depending on the type of port.)

	       The operational(1) status indicates that the port
	       is enabled (see ocRptrPortAdminStatus) and working,
	       even though it might be auto-partitioned (see
	       ocRptrPortAutoPartitionState).

	       If this object has the value operational(1) and
	       ocRptrPortAdminStatus is set to disabled(2), it is
	       expected that this object's value will change to
	       notOperational(2) soon after."
       ::= { ocRptrPortEntry 7 }



--
--		      The MONITOR GROUP
--
-- Implementation of this group is optional, but within the
-- group all elements are mandatory.  If a managed repeater
-- implements any part of this group, the entire group shall
-- be implemented.

--
-- Repeater Monitor Information
--
-- Performance monitoring statistics for the repeater
--


ocRptrMonitorRptrTable OBJECT-TYPE
       SYNTAX	 SEQUENCE OF OcRptrMonitorRptrEntry
       ACCESS	 not-accessible
       STATUS	 mandatory
       DESCRIPTION
	       "Table of performance and error statistics for the
		Repeater."
       ::= { ocRptrMonitorRptrInfo 1 }


ocRptrMonitorRptrEntry OBJECT-TYPE
       SYNTAX	 OcRptrMonitorRptrEntry

       ACCESS	 not-accessible
       STATUS	 mandatory
       DESCRIPTION
	       "An entry in the table, containing total
	       performance and error statistics for a
	       repeater."
       INDEX	{ ocRptrMonitorSlotIndex, ocRptrMonitorNetID }
       ::= { ocRptrMonitorRptrTable 1 }

   OcRptrMonitorRptrEntry ::=
       SEQUENCE {
	   ocRptrMonitorSlotIndex
	       INTEGER,
	   ocRptrMonitorNetID
	       INTEGER,
	   ocRptrMonitorTransmitCollisions
	       Counter
       }


ocRptrMonitorSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrMonitorNetID
		resides. If ocRptrMonitorNetID does not identify
		an isolated network, then the value of this object is
		backplane(255)."
	::= {ocRptrMonitorRptrEntry  1 }

ocRptrMonitorNetID OBJECT-TYPE
	 SYNTAX INTEGER {
		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this repeater."
       ::= {ocRptrMonitorRptrEntry 2 }

ocRptrMonitorTransmitCollisions OBJECT-TYPE
       SYNTAX	 Counter
       ACCESS	 read-only
       STATUS	 mandatory
       DESCRIPTION
	       "This counter is incremented every time the
	       repeater state machine enters the TRANSMIT
	       COLLISION state from any state other than ONE PORT
	       LEFT (Ref: Fig 9-2, IEEE 802.3 Std).

	       The approximate minimum time for rollover of this
	       counter is 16 hours."
       REFERENCE
	       "Reference IEEE 802.3 Rptr Mgt, 19.2.3.2,
	       aTransmitCollisions."
       ::= { ocRptrMonitorRptrEntry 3 }


   --
   -- The Group Monitor Table
   --


   --
   -- Basic Repeater Information
   --
   -- Configuration, status, and control objects for the overall
   -- repeater
   --

ocRptrMonitorGroupTable OBJECT-TYPE
       SYNTAX	 SEQUENCE OF OcRptrMonitorGroupEntry
       ACCESS	 not-accessible
       STATUS	 mandatory
       DESCRIPTION
	       "Table of performance and error statistics for the
	       groups."
       ::= { ocRptrMonitorGroupInfo 1 }


ocRptrMonitorGroupEntry OBJECT-TYPE
       SYNTAX	 OcRptrMonitorGroupEntry

       ACCESS	 not-accessible
       STATUS	 mandatory
       DESCRIPTION
	       "An entry in the table, containing total
	       performance and error statistics for a single
	       group.  Regular retrieval of the information in
	       this table provides a means of tracking the
	       performance and health of the networked devices
	       attached to this group's ports.

	       The counters in this table are redundant in the
	       sense that they are the summations of information
	       already available through other objects.  However,
	       these sums provide a considerable optimization of
	       network management traffic over the otherwise
	       necessary retrieval of the individual counters
	       included in each sum."
       INDEX	{ ocRptrMonitorGroupSlotIndex, ocRptrMonitorGroupNetID, ocRptrMonitorGroupIndex }
       ::= { ocRptrMonitorGroupTable 1 }

   OcRptrMonitorGroupEntry ::=
       SEQUENCE {
	   ocRptrMonitorGroupSlotIndex
	       INTEGER,
	   ocRptrMonitorGroupNetID
	       INTEGER,
	   ocRptrMonitorGroupIndex
	       INTEGER,
	   ocRptrMonitorGroupTotalFrames
	       Counter,
	   ocRptrMonitorGroupTotalOctets
	       Counter,
	   ocRptrMonitorGroupTotalErrors
	       Counter
       }


ocRptrMonitorGroupSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrMonitorGroupNetID
		resides. If ocRptrMonitorGroupNetID does not identify
		an isolated network, then the value of this object is
		backplane(255)."
	::= {ocRptrMonitorGroupEntry  1 }

ocRptrMonitorGroupNetID OBJECT-TYPE
	 SYNTAX INTEGER {
		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this group's repeater."
       ::= {ocRptrMonitorGroupEntry 2 }

ocRptrMonitorGroupIndex OBJECT-TYPE
       SYNTAX	 INTEGER (1..1024)
       ACCESS	 read-only
       STATUS	 mandatory
       DESCRIPTION
	       "This object identifies the group within the
	       repeater for which this entry contains
	       information."
       ::= { ocRptrMonitorGroupEntry 3 }

ocRptrMonitorGroupTotalFrames OBJECT-TYPE
       SYNTAX	 Counter
       ACCESS	 read-only
       STATUS	 mandatory
       DESCRIPTION
	       "The total number of frames of valid frame length

	       that have been received on the ports in this
	       group.  This counter is the summation of the
	       values of the ocRptrMonitorPortReadableFrames
	       counters for all of the ports in the group.

	       This statistic provides one of the parameters
	       necessary for obtaining the packet error rate.
	       The approximate minimum time for rollover of this
	       counter is 80 hours."
       ::= { ocRptrMonitorGroupEntry 4 }

ocRptrMonitorGroupTotalOctets OBJECT-TYPE
       SYNTAX	 Counter
       ACCESS	 read-only
       STATUS	 mandatory
       DESCRIPTION
	       "The total number of octets contained in the valid
	       frames that have been received on the ports in
	       this group.  This counter is the summation of the
	       values of the ocRptrMonitorPortReadableOctets
	       counters for all of the ports in the group.

	       This statistic provides an indicator of the total
	       data transferred.  The approximate minimum time
	       for rollover of this counter is 58 minutes."
       ::= { ocRptrMonitorGroupEntry 5 }

ocRptrMonitorGroupTotalErrors OBJECT-TYPE
       SYNTAX	 Counter
       ACCESS	 read-only
       STATUS	 mandatory
       DESCRIPTION
	       "The total number of errors which have occurred on
	       all of the ports in this group.  This counter is
	       the summation of the values of the
	       ocRptrMonitorPortTotalErrors counters for all of the
	       ports in the group."
       ::= { ocRptrMonitorGroupEntry 6 }


   --
   -- The Port Monitor Table
   --

ocRptrMonitorPortTable OBJECT-TYPE
       SYNTAX	 SEQUENCE OF OcRptrMonitorPortEntry
       ACCESS	 not-accessible
       STATUS	 mandatory

       DESCRIPTION
	       "Table of performance and error statistics for the
	       ports."
       ::= { ocRptrMonitorPortInfo 1 }

ocRptrMonitorPortEntry OBJECT-TYPE
       SYNTAX	 OcRptrMonitorPortEntry
       ACCESS	 not-accessible
       STATUS	 mandatory
       DESCRIPTION
	       "An entry in the table, containing performance and
	       error statistics for a single port."
       INDEX	{ ocRptrMonitorPortSlotIndex, ocRptrMonitorPortNetID, ocRptrMonitorPortGroupIndex, ocRptrMonitorPortIndex }
       ::= { ocRptrMonitorPortTable 1 }

   OcRptrMonitorPortEntry ::=
       SEQUENCE {
	   ocRptrMonitorPortSlotIndex
	       INTEGER,
	   ocRptrMonitorPortNetID
	       INTEGER,
	   ocRptrMonitorPortGroupIndex
	       INTEGER,
	   ocRptrMonitorPortIndex
	       INTEGER,
	   ocRptrMonitorPortReadableFrames
	       Counter,
	   ocRptrMonitorPortReadableOctets
	       Counter,
	   ocRptrMonitorPortFCSErrors
	       Counter,
	   ocRptrMonitorPortAlignmentErrors
	       Counter,
	   ocRptrMonitorPortFrameTooLongs
	       Counter,
	   ocRptrMonitorPortShortEvents
	       Counter,
	   ocRptrMonitorPortRunts
	       Counter,
	   ocRptrMonitorPortCollisions
	       Counter,
	   ocRptrMonitorPortLateEvents
	       Counter,
	   ocRptrMonitorPortVeryLongEvents
	       Counter,
	   ocRptrMonitorPortDataRateMismatches
	       Counter,
	   ocRptrMonitorPortAutoPartitions
	       Counter,
	   ocRptrMonitorPortTotalErrors
	       Counter
       }


ocRptrMonitorPortSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrMonitorPortNetID
		resides. If ocRptrMonitorPortNetID does not identify
		an isolated network, then the value of this object is
		backplane(255)."
	::= {ocRptrMonitorPortEntry 1 }

ocRptrMonitorPortNetID OBJECT-TYPE
	 SYNTAX INTEGER {
		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this port's repeater."
       ::= {ocRptrMonitorPortEntry 2 }

ocRptrMonitorPortGroupIndex OBJECT-TYPE
       SYNTAX	 INTEGER (1..1024)
       ACCESS	 read-only
       STATUS	 mandatory
       DESCRIPTION
	       "This object identifies the group containing the
	       port for which this entry contains information."
       ::= { ocRptrMonitorPortEntry 3 }

ocRptrMonitorPortIndex OBJECT-TYPE
       SYNTAX	 INTEGER (1..1024)
       ACCESS	 read-only
       STATUS	 mandatory
       DESCRIPTION
	       "This object identifies the port within the group
	       for which this entry contains information."
       REFERENCE
	       "Reference IEEE 802.3 Rptr Mgt, 19.2.6.2,
	       aPortID."
       ::= { ocRptrMonitorPortEntry 4 }

ocRptrMonitorPortReadableFrames OBJECT-TYPE
       SYNTAX	 Counter
       ACCESS	 read-only
       STATUS	 mandatory
       DESCRIPTION
	       "This object is the number of frames of valid
	       frame length that have been received on this port.
	       This counter is incremented by one for each frame
	       received on this port whose OctetCount is greater
	       than or equal to minFrameSize and less than or
	       equal to maxFrameSize (Ref: IEEE 802.3 Std,
	       4.4.2.1) and for which the FCSError and
	       CollisionEvent signals are not asserted.

	       This statistic provides one of the parameters
	       necessary for obtaining the packet error rate.
	       The approximate minimum time for rollover of this
	       counter is 80 hours."
       REFERENCE
	       "Reference IEEE 802.3 Rptr Mgt, 19.2.6.2,
	       aReadableFrames."
       ::= { ocRptrMonitorPortEntry 5 }

ocRptrMonitorPortReadableOctets OBJECT-TYPE
       SYNTAX	 Counter
       ACCESS	 read-only
       STATUS	 mandatory

       DESCRIPTION
	       "This object is the number of octets contained in
	       valid frames that have been received on this port.
	       This counter is incremented by OctetCount for each
	       frame received on this port which has been
	       determined to be a readable frame.

	       This statistic provides an indicator of the total
	       data transferred.  The approximate minimum time
	       for rollover of this counter is 58 minutes."
       REFERENCE
	       "Reference IEEE 802.3 Rptr Mgt, 19.2.6.2,
	       aReadableOctets."
       ::= { ocRptrMonitorPortEntry 6 }

ocRptrMonitorPortFCSErrors OBJECT-TYPE
       SYNTAX	 Counter
       ACCESS	 read-only
       STATUS	 mandatory
       DESCRIPTION
	       "This counter is incremented by one for each frame
	       received on this port with the FCSError signal
	       asserted and the FramingError and CollisionEvent
	       signals deasserted and whose OctetCount is greater
	       than or equal to minFrameSize and less than or
	       equal to maxFrameSize (Ref: 4.4.2.1, IEEE 802.3
	       Std).

	       The approximate minimum time for rollover of this
	       counter is 80 hours."
       REFERENCE
	       "Reference IEEE 802.3 Rptr Mgt, 19.2.6.2,
	       aFrameCheckSequenceErrors."
       ::= { ocRptrMonitorPortEntry 7 }

ocRptrMonitorPortAlignmentErrors OBJECT-TYPE
       SYNTAX	 Counter
       ACCESS	 read-only
       STATUS	 mandatory
       DESCRIPTION
	       "This counter is incremented by one for each frame
	       received on this port with the FCSError and
	       FramingError signals asserted and CollisionEvent
	       signal deasserted and whose OctetCount is greater
	       than or equal to minFrameSize and less than or
	       equal to maxFrameSize (Ref: IEEE 802.3 Std,
	       4.4.2.1).  If ocRptrMonitorPortAlignmentErrors is
	       incremented then the ocRptrMonitorPortFCSErrors

	       Counter shall not be incremented for the same
	       frame.

	       The approximate minimum time for rollover of this
	       counter is 80 hours."
       REFERENCE
	       "Reference IEEE 802.3 Rptr Mgt, 19.2.6.2,
	       aAlignmentErrors."
       ::= { ocRptrMonitorPortEntry 8 }

ocRptrMonitorPortFrameTooLongs OBJECT-TYPE
       SYNTAX	 Counter
       ACCESS	 read-only
       STATUS	 mandatory
       DESCRIPTION
	       "This counter is incremented by one for each frame
	       received on this port whose OctetCount is greater
	       than maxFrameSize (Ref: 4.4.2.1, IEEE 802.3 Std).
	       If ocRptrMonitorPortFrameTooLongs is incremented
	       then neither the ocRptrMonitorPortAlignmentErrors
	       nor the ocRptrMonitorPortFCSErrors counter shall be
	       incremented for the frame.

	       The approximate minimum time for rollover of this
	       counter is 61 days."
       REFERENCE
	       "Reference IEEE 802.3 Rptr Mgt, 19.2.6.2,
	       aFramesTooLong."
       ::= { ocRptrMonitorPortEntry 9 }

ocRptrMonitorPortShortEvents OBJECT-TYPE
       SYNTAX	 Counter
       ACCESS	 read-only
       STATUS	 mandatory
       DESCRIPTION
	       "This counter is incremented by one for each
	       CarrierEvent on this port with ActivityDuration
	       less than ShortEventMaxTime.  ShortEventMaxTime is
	       greater than 74 bit times and less than 82 bit
	       times.  ShortEventMaxTime has tolerances included
	       to provide for circuit losses between a
	       conformance test point at the AUI and the
	       measurement point within the state machine.

	       Note:  shortEvents may indicate externally
	       generated noise hits which will cause the repeater
	       to transmit Runts to its other ports, or propagate
	       a collision (which may be late) back to the

	       transmitting DTE and damaged frames to the rest of
	       the network.

	       Implementors may wish to consider selecting the
	       ShortEventMaxTime towards the lower end of the
	       allowed tolerance range to accommodate bit losses
	       suffered through physical channel devices not
	       budgeted for within this standard.

	       The approximate minimum time for rollover of this
	       counter is 16 hours."
       REFERENCE
	       "Reference IEEE 802.3 Rptr Mgt, 19.2.6.2,
	       aShortEvents."
       ::= { ocRptrMonitorPortEntry 10 }

ocRptrMonitorPortRunts OBJECT-TYPE
       SYNTAX	 Counter
       ACCESS	 read-only
       STATUS	 mandatory
       DESCRIPTION
	       "This counter is incremented by one for each
	       CarrierEvent on this port that meets one of the
	       following two conditions.  Only one test need be
	       made.  a) The ActivityDuration is greater than
	       ShortEventMaxTime and less than ValidPacketMinTime
	       and the CollisionEvent signal is deasserted.  b)
	       The OctetCount is less than 64, the
	       ActivityDuration is greater than ShortEventMaxTime
	       and the CollisionEvent signal is deasserted.
	       ValidPacketMinTime is greater than or equal to 552
	       bit times and less than 565 bit times.

	       An event whose length is greater than 74 bit times
	       but less than 82 bit times shall increment either
	       the shortEvents counter or the runts counter but
	       not both.  A CarrierEvent greater than or equal to
	       552 bit times but less than 565 bit times may or
	       may not be counted as a runt.

	       ValidPacketMinTime has tolerances included to
	       provide for circuit losses between a conformance
	       test point at the AUI and the measurement point
	       within the state machine.

	       Runts usually indicate collision fragments, a
	       normal network event.  In certain situations
	       associated with large diameter networks a

	       percentage of runts may exceed ValidPacketMinTime.

	       The approximate minimum time for rollover of this
	       counter is 16 hours."
       REFERENCE
	       "Reference IEEE 802.3 Rptr Mgt, 19.2.6.2, aRunts."
       ::= { ocRptrMonitorPortEntry 11 }

ocRptrMonitorPortCollisions OBJECT-TYPE
       SYNTAX	 Counter
       ACCESS	 read-only
       STATUS	 mandatory
       DESCRIPTION
	       "This counter is incremented by one for any
	       CarrierEvent signal on any port for which the
	       CollisionEvent signal on this port is asserted.

	       The approximate minimum time for rollover of this
	       counter is 16 hours."
       REFERENCE
	       "Reference IEEE 802.3 Rptr Mgt, 19.2.6.2,
	       aCollisions."
       ::= { ocRptrMonitorPortEntry 12 }

ocRptrMonitorPortLateEvents OBJECT-TYPE
       SYNTAX	 Counter
       ACCESS	 read-only
       STATUS	 mandatory
       DESCRIPTION
	       "This counter is incremented by one for each
	       CarrierEvent on this port in which the CollIn(X)
	       variable transitions to the value SQE (Ref:
	       9.6.6.2, IEEE 802.3 Std) while the
	       ActivityDuration is greater than the
	       LateEventThreshold.  Such a CarrierEvent is
	       counted twice, as both a collision and as a
	       lateEvent.

	       The LateEventThreshold is greater than 480 bit
	       times and less than 565 bit times.
	       LateEventThreshold has tolerances included to
	       permit an implementation to build a single
	       threshold to serve as both the LateEventThreshold
	       and ValidPacketMinTime threshold.

	       The approximate minimum time for rollover of this
	       counter is 81 hours."
       REFERENCE

	       "Reference IEEE 802.3 Rptr Mgt, 19.2.6.2,
	       aLateEvents."
       ::= { ocRptrMonitorPortEntry 13 }

ocRptrMonitorPortVeryLongEvents OBJECT-TYPE
       SYNTAX	 Counter
       ACCESS	 read-only
       STATUS	 mandatory
       DESCRIPTION
	       "This counter is incremented by one for each
	       CarrierEvent on this port whose ActivityDuration
	       is greater than the MAU Jabber Lockup Protection
	       timer TW3 (Ref: 9.6.1 & 9.6.5, IEEE 802.3 Std).
	       Other counters may be incremented as appropriate."
       REFERENCE
	       "Reference IEEE 802.3 Rptr Mgt, 19.2.6.2,
	       aVeryLongEvents."
       ::= { ocRptrMonitorPortEntry 14 }

ocRptrMonitorPortDataRateMismatches OBJECT-TYPE
       SYNTAX	 Counter
       ACCESS	 read-only
       STATUS	 mandatory
       DESCRIPTION
	       "This counter is incremented by one for each frame
	       received on this port that meets all of the
	       following conditions:  a) The CollisionEvent
	       signal is not asserted.  b) The ActivityDuration
	       is greater than ValidPacketMinTime.  c) The
	       frequency (data rate) is detectably mismatched
	       from the local transmit frequency.  The exact
	       degree of mismatch is vendor specific and is to be
	       defined by the vendor for conformance testing.

	       When this event occurs, other counters whose
	       increment conditions were satisfied may or may not
	       also be incremented, at the implementor's
	       discretion.  Whether or not the repeater was able
	       to maintain data integrity is beyond the scope of
	       this standard."
       REFERENCE
	       "Reference IEEE 802.3 Rptr Mgt, 19.2.6.2,
	       aDataRateMismatches."
       ::= { ocRptrMonitorPortEntry 15 }

ocRptrMonitorPortAutoPartitions OBJECT-TYPE
       SYNTAX	 Counter
       ACCESS	 read-only

       STATUS	 mandatory
       DESCRIPTION
	       "This counter is incremented by one for each time
	       the repeater has automatically partitioned this
	       port.  The conditions that cause port partitioning
	       are specified in the partition state machine in
	       Section 9 [IEEE 802.3 Std].  They are not
	       differentiated here."
       REFERENCE
	       "Reference IEEE 802.3 Rptr Mgt, 19.2.6.2,
	       aAutoPartitions."
       ::= { ocRptrMonitorPortEntry 16 }

ocRptrMonitorPortTotalErrors OBJECT-TYPE
       SYNTAX	 Counter
       ACCESS	 read-only
       STATUS	 mandatory
       DESCRIPTION
	       "The total number of errors which have occurred on
	       this port.  This counter is the summation of the
	       values of other error counters (for the same
	       port), namely:

		   ocRptrMonitorPortFCSErrors,
		   ocRptrMonitorPortAlignmentErrors,
		   ocRptrMonitorPortFrameTooLongs,
		   ocRptrMonitorPortShortEvents,
		   ocRptrMonitorPortLateEvents,
		   ocRptrMonitorPortVeryLongEvents, and
		   ocRptrMonitorPortDataRateMismatches.

	       This counter is redundant in the sense that it is
	       the summation of information already available
	       through other objects.  However, it is included
	       specifically because the regular retrieval of this
	       object as a means of tracking the health of a port
	       provides a considerable optimization of network
	       management traffic over the otherwise necessary
	       retrieval of the summed counters."
       ::= { ocRptrMonitorPortEntry 17 }


   --
   --			 The ADDRESS TRACKING GROUP
   --
   -- Implementation of this group is optional; it is appropriate
   -- for all systems which have the necessary metering.  If a
   -- managed repeater implements any part of this group, the entire

   -- group shall be implemented.

   --
   -- The Port Address Tracking Table
   --

ocRptrAddrTrackTable OBJECT-TYPE
       SYNTAX	 SEQUENCE OF OcRptrAddrTrackEntry
       ACCESS	 not-accessible
       STATUS	 mandatory
       DESCRIPTION
	       "Table of address mapping information about the
	       ports."
       ::= { ocRptrAddrTrackPortInfo 1 }

ocRptrAddrTrackEntry OBJECT-TYPE
       SYNTAX	 OcRptrAddrTrackEntry
       ACCESS	 not-accessible
       STATUS	 mandatory
       DESCRIPTION
	       "An entry in the table, containing address mapping
	       information about a single port."
       INDEX	{ ocRptrAddrTrackSlotIndex, ocRptrAddrTrackGroupNetID, ocRptrAddrTrackGroupIndex, ocRptrAddrTrackPortIndex }
       ::= { ocRptrAddrTrackTable 1 }

   OcRptrAddrTrackEntry ::=
       SEQUENCE {
	   ocRptrAddrTrackSlotIndex
	       INTEGER,
	   ocRptrAddrTrackGroupNetID
	       INTEGER,
	   ocRptrAddrTrackGroupIndex
	       INTEGER,
	   ocRptrAddrTrackPortIndex
	       INTEGER,
	   ocRptrAddrTrackLastSourceAddress
	       MacAddress,
	   ocRptrAddrTrackSourceAddrChanges
	       Counter,
	   ocRptrAddrTrackNewLastSrcAddress
	       OCTET STRING
       }


ocRptrAddrTrackSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		backplane(255)
		}
	ACCESS read-only
	STATUS mandatory
	DESCRIPTION
		"The slot number of the repeater module on which
		the isolated network identified by ocRptrMonitorGroupNetID
		resides. If ocRptrMonitorGroupNetID does not identify
		an isolated network, then the value of this object is
		backplane(255)."
	::= {ocRptrAddrTrackEntry 1 }

ocRptrAddrTrackGroupNetID OBJECT-TYPE
	 SYNTAX INTEGER {
		 ethernet-1(6),
		 ethernet-2(7),
		 ethernet-3(8),

		 ethernet-4(32),
		 ethernet-5(33),
		 ethernet-6(34),
		 ethernet-7(35),
		 ethernet-8(36)
		 }
	 ACCESS read-only
	 STATUS mandatory
	 DESCRIPTION
		 "The network index that uniquely identifies this port's repeater."
       ::= { ocRptrAddrTrackEntry 2 }

ocRptrAddrTrackGroupIndex OBJECT-TYPE
       SYNTAX	 INTEGER (1..1024)
       ACCESS	 read-only
       STATUS	 mandatory
       DESCRIPTION
	       "This object identifies the group containing the
	       port for which this entry contains information."
       ::= { ocRptrAddrTrackEntry 3 }

ocRptrAddrTrackPortIndex OBJECT-TYPE
       SYNTAX	 INTEGER (1..1024)

       ACCESS	 read-only
       STATUS	 mandatory
       DESCRIPTION
	       "This object identifies the port within the group
	       for which this entry contains information."
       REFERENCE
	       "Reference IEEE 802.3 Rptr Mgt, 19.2.6.2,
	       aPortID."
       ::= { ocRptrAddrTrackEntry 4 }

ocRptrAddrTrackLastSourceAddress OBJECT-TYPE
       SYNTAX	 MacAddress
       ACCESS	 read-only
       STATUS	 mandatory
       DESCRIPTION
	       "This object is the SourceAddress of the last
	       readable frame (i.e., counted by
	       ocRptrMonitorPortReadableFrames) received by this
	       port."
       REFERENCE
	       "Reference IEEE 802.3 Rptr Mgt, 19.2.6.2,
	       aLastSourceAddress."
       ::= { ocRptrAddrTrackEntry 5 }

ocRptrAddrTrackSourceAddrChanges OBJECT-TYPE
       SYNTAX	 Counter
       ACCESS	 read-only
       STATUS	 mandatory
       DESCRIPTION
	       "This counter is incremented by one for each time
	       that the ocRptrAddrTrackLastSourceAddress attribute
	       for this port has changed.

	       This may indicate whether a link is connected to a
	       single DTE or another multi-user segment.
	       The approximate minimum time for rollover of this
	       counter is 81 hours."
       REFERENCE
	       "Reference IEEE 802.3 Rptr Mgt, 19.2.6.2,
	       aSourceAddressChanges."
       ::= { ocRptrAddrTrackEntry 6 }

ocRptrAddrTrackNewLastSrcAddress OBJECT-TYPE
       SYNTAX	 OCTET STRING (SIZE(0..6))
       ACCESS	 read-only
       STATUS	 mandatory
       DESCRIPTION
	       "This object is the SourceAddress of the last
	       readable frame (i.e., counted by
	       ocRptrMonitorPortReadableFrames) received by this
	       port.  If no frames have been received by this
	       port since the agent began monitoring the port
	       activity, the agent shall return a string of
	       length zero."
       REFERENCE
	       "Reference IEEE 802.3 Rptr Mgt, 19.2.6.2,
	       aLastSourceAddress."
       ::= { ocRptrAddrTrackEntry 7 }




 -- The trnet Group

 -- This group represents information about Token Ring networks.

trnetMapState OBJECT-TYPE
	 SYNTAX INTEGER {
		 changing(1),
		 notChanging(2)
		 }
	 ACCESS read-only
	 STATUS mandatory
	 DESCRIPTION
		"The state of the inter-module token ring map. If the map
		is being updated, then the state of the map is changing."
	 ::= { trnet 1 }


trnetStatsTable OBJECT-TYPE
	SYNTAX SEQUENCE OF TrnetStatsEntry
	ACCESS not-accessible
	STATUS mandatory
	DESCRIPTION
		"A list of Token Ring statistics entries counted
		for each network."
	::= { trnet 2 }

trnetStatsEntry OBJECT-TYPE
	SYNTAX TrnetStatsEntry
	ACCESS not-accessible
	STATUS mandatory
	DESCRIPTION
		"A collection of statistics kept for a particular
		Token Ring interface."
	INDEX { trnetStatsNetID }
	::= { trnetStatsTable 1 }

TrnetStatsEntry ::=
	SEQUENCE {
		trnetStatsNetID
			INTEGER,
		trnetStatsLineErrors
			Counter,
		trnetStatsBurstErrors
			Counter,
		trnetStatsACErrors
			Counter,
		trnetStatsLostFrameErrors
			Counter,
		trnetStatsCongestionErrors
			Counter,
		trnetStatsFrameCopiedErrors
			Counter,
		trnetStatsTokenErrors
			Counter,
		trnetStatsDuplicateAddresses
			Counter,
		trnetStatsBeaconEvents
			Counter,
		trnetStatsLastBeaconSender
			OCTET STRING,
		trnetStatsLastBeaconNAUN
			OCTET STRING,
		trnetStatsLastBeaconTime
			TimeTicks,
		trnetStatsLastBeaconAction
			INTEGER,
		trnetStatsTotalStations
			INTEGER,
		trnetStatsConcStations
			INTEGER,
		trnetStatsTotalPorts
			INTEGER,
		trnetStatsEnabledPorts
			INTEGER,
		trnetStatsActivePorts
			INTEGER
		}

trnetStatsNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trnetStatsEntry 1 }

trnetStatsLineErrors OBJECT-TYPE
	SYNTAX Counter
	ACCESS read-only
	STATUS mandatory
	DESCRIPTION
		"The total number of line errors reported in
		error reporting packets detected by the TRMM."
	::= { trnetStatsEntry 2 }

trnetStatsBurstErrors OBJECT-TYPE
	SYNTAX Counter
	ACCESS read-only
	STATUS mandatory
	DESCRIPTION
		"The total number of burst errors reported in
		error reporting packets detected by the TRMM."
	::= { trnetStatsEntry 3 }

trnetStatsACErrors OBJECT-TYPE
	SYNTAX Counter
	ACCESS read-only
	STATUS mandatory
	DESCRIPTION
		"The total number of AC (Address Copied) errors
		reported in error reporting packets detected by
		the TRMM."
	::= { trnetStatsEntry 4 }

trnetStatsLostFrameErrors OBJECT-TYPE
	SYNTAX Counter
	ACCESS read-only
	STATUS mandatory
	DESCRIPTION
		"The total number of lost frame errors reported
		in error reporting packets detected by the TRMM."
	::= { trnetStatsEntry 5 }

trnetStatsCongestionErrors OBJECT-TYPE
	SYNTAX Counter
	ACCESS read-only
	STATUS mandatory
	DESCRIPTION
		"The total number of receive congestion errors
		reported in error reporting packets detected by
		the TRMM."
	::= { trnetStatsEntry 6 }

trnetStatsFrameCopiedErrors OBJECT-TYPE
	SYNTAX Counter
	ACCESS read-only
	STATUS mandatory
	DESCRIPTION
		"The total number of frame copied errors
		reported in error reporting packets detected by
		the TRMM."
	::= { trnetStatsEntry 7 }

trnetStatsTokenErrors OBJECT-TYPE
	SYNTAX Counter
	ACCESS read-only
	STATUS mandatory
	DESCRIPTION
		"The total number of token errors reported in
		error reporting packets detected by the TRMM."
	::= { trnetStatsEntry 8 }

trnetStatsDuplicateAddresses OBJECT-TYPE
	SYNTAX Counter
	ACCESS read-only
	STATUS mandatory
	DESCRIPTION
		"The total number of token errors reported in
		error reporting packets detected by the TRMM."
	::= { trnetStatsEntry 9 }

trnetStatsBeaconEvents OBJECT-TYPE
	SYNTAX Counter
	ACCESS read-only
	STATUS mandatory
	DESCRIPTION
		"The total number of times that the ring enters
		the beaconing state."
	::= { trnetStatsEntry 10 }

trnetStatsLastBeaconSender OBJECT-TYPE
	SYNTAX OCTET STRING (SIZE(6))
	ACCESS read-only
	STATUS mandatory
	DESCRIPTION
		"The address of the sender of the last beacon frame
		received on this ring. If no beacon frames have been
		received, this object will be six zero octets."
	::= { trnetStatsEntry 11 }

trnetStatsLastBeaconNAUN OBJECT-TYPE
	SYNTAX OCTET STRING (SIZE(6))
	ACCESS read-only
	STATUS mandatory
	DESCRIPTION
		"The address of the NAUN in the last beacon frame
		received on this ring. If no beacon frames have been
		received, this object will be six zero octets."
	::= { trnetStatsEntry 12 }

trnetStatsLastBeaconTime OBJECT-TYPE
	SYNTAX TimeTicks
	ACCESS read-only
	STATUS mandatory
	DESCRIPTION
		"The time in in hundredths of a second since the last
		beacon event occurred.  For example, if the time  is 500
		ticks, then this event was seen 5 seconds ago. If no
		beacon events have occurred, then this will be equal
		to the sysUpTime."
	::= { trnetStatsEntry 13 }

trnetStatsLastBeaconAction OBJECT-TYPE
	SYNTAX INTEGER {
		noAction (1),
		portDisable (2),
		trunkDisable (3),
		moduleIsolate (4)
		}
	ACCESS read-only
	STATUS mandatory
	DESCRIPTION
		"The action (if any) taken to correct the last beacon
		event on the ring."
	::= { trnetStatsEntry 14 }

trnetStatsTotalStations OBJECT-TYPE
	SYNTAX INTEGER (1..255)
	ACCESS read-only
	STATUS mandatory
	DESCRIPTION
		"The number of stations currently participating in the 802.5
		MAC protocol on the ring."
	::= { trnetStatsEntry 15 }

trnetStatsConcStations OBJECT-TYPE
	SYNTAX INTEGER (1..255)
	ACCESS read-only
	STATUS mandatory
	DESCRIPTION
		"The number of stations currently participating in the 802.5
		MAC protocol on the ring which are connected to ports in
		this concentrator."
	::= { trnetStatsEntry 16}

trnetStatsTotalPorts OBJECT-TYPE
	SYNTAX INTEGER
	ACCESS read-only
	STATUS mandatory
	DESCRIPTION
		"The total number of ports within this concentrator and
		on this ring regardless of their admin state or status."
	::= { trnetStatsEntry 17 }

trnetStatsEnabledPorts OBJECT-TYPE
	SYNTAX INTEGER
	ACCESS read-only
	STATUS mandatory
	DESCRIPTION
		"The number of ports within this concentrator and on this ring
		which have portAdminState set to enabled."
	::= { trnetStatsEntry 18 }

trnetStatsActivePorts OBJECT-TYPE
	SYNTAX INTEGER
	ACCESS read-only
	STATUS mandatory
	DESCRIPTION
		"The number of ports within this concentrator and on this ring
		which have portAdminState set to enabled and whose
		portStatus has a status of okay."
	::= { trnetStatsEntry 19 }

trnetStatsStationTable OBJECT-TYPE
	SYNTAX SEQUENCE OF TrnetStatsStationEntry
	ACCESS not-accessible
	STATUS mandatory
	DESCRIPTION
		"A list of ring statistics entries."
	::= { trnet 3 }

trnetStatsStationEntry OBJECT-TYPE
	SYNTAX TrnetStatsStationEntry
	ACCESS not-accessible
	STATUS mandatory
	DESCRIPTION
		"A collection of statistics for a particular station
		that has been discovered on a a ring monitored by
		this device."
	INDEX { trnetStatsStationNetID, trnetStatsStationAddr }
	::= { trnetStatsStationTable 1 }

TrnetStatsStationEntry ::=
	SEQUENCE {
		trnetStatsStationNetID
			INTEGER,
		trnetStatsStationAddr
			OCTET STRING,
		trnetStatsStationSlotIndex
			INTEGER,
		trnetStatsStationPortIndex
			INTEGER,
		trnetStatsStationNAUNAddress
			OCTET STRING,
		trnetStatsStationLineErrors
			Counter,
		trnetStatsStationBurstErrors
			Counter,
		trnetStatsStationACErrors
			Counter,
		trnetStatsStationLostFrameErrors
			Counter,
		trnetStatsStationCongestionErrors
			Counter,
		trnetStatsStationFrameCopiedErrors
			Counter,
		trnetStatsStationTokenErrors
			Counter,
		trnetStatsStationDuplicateAddresses
			Counter
		}

trnetStatsStationNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trnetStatsStationEntry 1 }

trnetStatsStationAddr OBJECT-TYPE
	SYNTAX OCTET STRING (SIZE(6))
	ACCESS read-only
	STATUS mandatory
	DESCRIPTION
		"The physical address of this station."
	::= { trnetStatsStationEntry 2 }

trnetStatsStationSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		external(255)
		}
	ACCESS read-only
	STATUS mandatory
	DESCRIPTION
		"The slot number of the station with this address.
		Addresses with a slot value of external(255) are
		not in this concentrator."
	::= { trnetStatsStationEntry 3 }

trnetStatsStationPortIndex OBJECT-TYPE
	SYNTAX INTEGER
	ACCESS read-only
	STATUS mandatory
	DESCRIPTION
		"The port number within trnetStatsStationSlotIndex's
		slot that received this address. If
		trnetStatsStationSlotIndex has a value of
		external(255), then the port address will be 255."
	::= { trnetStatsStationEntry 4 }

trnetStatsStationNAUNAddress OBJECT-TYPE
	SYNTAX OCTET STRING (SIZE(6))
	ACCESS read-only
	STATUS mandatory
	DESCRIPTION
		"The physical address of the nearest active upstream
		neighbor of this station."
	::= { trnetStatsStationEntry 5 }

trnetStatsStationLineErrors OBJECT-TYPE
	SYNTAX Counter
	ACCESS read-only
	STATUS mandatory
	DESCRIPTION
		"The total number of Line Errors pertaining to this station
		reported in error reporting packets detected by the TRMM."
	::= { trnetStatsStationEntry 6 }

trnetStatsStationBurstErrors OBJECT-TYPE
	SYNTAX Counter
	ACCESS read-only
	STATUS mandatory
	DESCRIPTION
		"The total number of burst errors pertaining to this station
		reported in error reporting packets detected by the TRMM."
	::= { trnetStatsStationEntry 7 }

trnetStatsStationACErrors OBJECT-TYPE
	SYNTAX Counter
	ACCESS read-only
	STATUS mandatory
	DESCRIPTION
		"The total number of AC (Address Copied)
		errors pertaining to this station reported in
		error reporting packets detected by the TRMM."
	::= { trnetStatsStationEntry 8 }

trnetStatsStationLostFrameErrors OBJECT-TYPE
	SYNTAX Counter
	ACCESS read-only
	STATUS mandatory
	DESCRIPTION
		"The total number of lost frame errors pertaining to
		this station reported in error reporting packets
		detected by the TRMM."
	::= { trnetStatsStationEntry 9 }

trnetStatsStationCongestionErrors OBJECT-TYPE
	SYNTAX Counter
	ACCESS read-only
	STATUS mandatory
	DESCRIPTION
		"The total number of congestion errors pertaining
		to this station reported in error reporting
		packets detected by the TRMM."
	::= { trnetStatsStationEntry 10 }

trnetStatsStationFrameCopiedErrors OBJECT-TYPE
	SYNTAX Counter
	ACCESS read-only
	STATUS mandatory
	DESCRIPTION
		"The total number of frame copied errors pertaining
		to this station reported in error reporting packets
		detected by the TRMM."
	::= { trnetStatsStationEntry 11 }

trnetStatsStationTokenErrors OBJECT-TYPE
	SYNTAX Counter
	ACCESS read-only
	STATUS mandatory
	DESCRIPTION
		"The total number of token errors pertaining to this
		station reported in error reporting packets detected
		by the TRMM."
	::= { trnetStatsStationEntry 12 }

trnetStatsStationDuplicateAddresses OBJECT-TYPE
	SYNTAX Counter
	ACCESS read-only
	STATUS mandatory
	DESCRIPTION
		"The number of times this station experienced
		a duplicate address error."
	::= { trnetStatsStationEntry 13 }


trnetStatsPortTable OBJECT-TYPE
	SYNTAX SEQUENCE OF TrnetStatsPortEntry
	ACCESS not-accessible
	STATUS mandatory
	DESCRIPTION
		"A list of statistic entries, for ports within the
		concentrator."
	::= { trnet 4 }

trnetStatsPortEntry OBJECT-TYPE
	SYNTAX TrnetStatsPortEntry
	ACCESS not-accessible
	STATUS mandatory
	DESCRIPTION
		"A collection of statistics for a particular station
		that has been discovered on a a ring monitored by
		this device."
	INDEX {trnetStatsPortSlotIndex, trnetStatsPortIndex }
	::= { trnetStatsPortTable 1 }

TrnetStatsPortEntry ::=
	SEQUENCE {
		trnetStatsPortSlotIndex
			INTEGER,
		trnetStatsPortIndex
			INTEGER,
		trnetStatsPortNetID
			INTEGER,
		trnetStatsPortTotalStations
			INTEGER,
		trnetStatsPortAddress
			OCTET STRING,
		trnetStatsPortLineErrors
			Counter,
		trnetStatsPortBurstErrors
			Counter,
		trnetStatsPortACErrors
			Counter,
		trnetStatsPortLostFrameErrors
			Counter,
		trnetStatsPortCongestionErrors
			Counter,
		trnetStatsPortFrameCopiedErrors
			Counter,
		trnetStatsPortTokenErrors
			Counter,
		trnetStatsPortDuplicateAddresses
			Counter
		}

trnetStatsPortSlotIndex OBJECT-TYPE
	SYNTAX INTEGER
	ACCESS read-only
	STATUS mandatory
	DESCRIPTION
		"The port slot number."
	::= { trnetStatsPortEntry 1 }

trnetStatsPortIndex OBJECT-TYPE
	SYNTAX INTEGER
	ACCESS read-only
	STATUS mandatory
	DESCRIPTION
		"The port number within trnetStatsPortSlotIndex's slot."
	::= { trnetStatsPortEntry 2 }

trnetStatsPortNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trnetStatsPortEntry 3 }

trnetStatsPortTotalStations OBJECT-TYPE
	SYNTAX INTEGER
	ACCESS read-only
	STATUS mandatory
	DESCRIPTION
		"The total number of stations attached to this port."
	::= { trnetStatsPortEntry 4 }

trnetStatsPortAddress OBJECT-TYPE
	SYNTAX OCTET STRING (SIZE(6))
	ACCESS read-only
	STATUS mandatory
	DESCRIPTION
		"The mac address of the station connected to this
		If there are multiple mac addresses for this port,
		then this object will contain the last mac address."
	::= { trnetStatsPortEntry 5 }

trnetStatsPortLineErrors OBJECT-TYPE
	SYNTAX Counter
	ACCESS read-only
	STATUS mandatory
	DESCRIPTION
		"The total number of Line Errors pertaining to
		this port reported in error reporting
		packets detected by the TRMM."
	::= { trnetStatsPortEntry 6 }

trnetStatsPortBurstErrors OBJECT-TYPE
	SYNTAX Counter
	ACCESS read-only
	STATUS mandatory
	DESCRIPTION
		"The total number of burst errors pertaining
		to this port reported in error reporting
		packets detected by the TRMM."
	::= { trnetStatsPortEntry 7 }

trnetStatsPortACErrors OBJECT-TYPE
	SYNTAX Counter
	ACCESS read-only
	STATUS mandatory
	DESCRIPTION
		"The total number of AC (Address Copied)
		errors pertaining to this port reported in
		error reporting packets detected by the TRMM."
	::= { trnetStatsPortEntry 8 }

trnetStatsPortLostFrameErrors OBJECT-TYPE
	SYNTAX Counter
	ACCESS read-only
	STATUS mandatory
	DESCRIPTION
		"The total number of lost frame errors pertaining to
		this port reported in error reporting packets
		detected by the TRMM."
	::= { trnetStatsPortEntry 9 }

trnetStatsPortCongestionErrors OBJECT-TYPE
	SYNTAX Counter
	ACCESS read-only
	STATUS mandatory
	DESCRIPTION
		"The total number of congestion errors pertaining
		to this port reported in error reporting
		packets detected by the TRMM."
	::= { trnetStatsPortEntry 10 }

trnetStatsPortFrameCopiedErrors OBJECT-TYPE
	SYNTAX Counter
	ACCESS read-only
	STATUS mandatory
	DESCRIPTION
		"The total number of frame copied errors pertaining
		to this port reported in error reporting packets
		detected by the TRMM."
	::= { trnetStatsPortEntry 11 }

trnetStatsPortTokenErrors OBJECT-TYPE
	SYNTAX Counter
	ACCESS read-only
	STATUS mandatory
	DESCRIPTION
		"The total number of token errors pertaining to this
		station reported in error reporting packets detected
		by the TRMM."
	::= { trnetStatsPortEntry 12 }

trnetStatsPortDuplicateAddresses OBJECT-TYPE
	SYNTAX Counter
	ACCESS read-only
	STATUS mandatory
	DESCRIPTION
		"The number of times this port experienced
		a duplicate address error."
	::= { trnetStatsPortEntry 13 }

trnetMapSummary		OBJECT IDENTIFIER ::= { trnet 5 }

trnetMapSummaryLogicalState OBJECT-TYPE
	SYNTAX INTEGER {
		changing(1),
		notChanging(2)
		}
	ACCESS read-only
	STATUS mandatory
	DESCRIPTION
		"The state of the token ring summary table. If the summary
		is being updated, then the state of the summary is changing."
	::= { trnetMapSummary 1 }

trnetMapSummaryLogicalLock OBJECT-TYPE
	SYNTAX INTEGER {
		lock(1),
		unlock(2)
		}
	ACCESS read-write
	STATUS mandatory
	DESCRIPTION
		"A semaphore for locking the token ring summary table.
		When locked, updates to the summary will pend until the
		semaphore is unlocked, so that a valid summary can be read.
		This cannot be set to unlock if trnetSummaryLogicalState is
		changing.
		For complete accuracy, this should be read after being set to
		ensure that the map was not changing when the lock was
		attempted. After the summary information has been recorded,
		the semaphore should be set to unlock to allow changes to
		occur."
	::= { trnetMapSummary 2 }

trnetMapSummaryTable OBJECT-TYPE
	SYNTAX SEQUENCE OF TrnetMapSummaryEntry
	ACCESS not-accessible
	STATUS mandatory
	DESCRIPTION
		"A logical map of the token ring network, starting from the
		agent's specified token ring interface. Each station on the
		map is represented by it's MAC address, slot number and port
		number (8 octets per station). If the port is external
		to the concentrator, the slot number and the port number will
		be 255. The map is ordered in the same
		direction as the token flow. The MAC addresses
		are concatonated into groups of up to 32 addresses per entry.
		This table supports up to 256 stations."
	::= { trnetMapSummary 3 }

trnetMapSummaryEntry OBJECT-TYPE
	SYNTAX TrnetMapSummaryEntry
	ACCESS not-accessible
	STATUS mandatory
	DESCRIPTION
		"A group of MAC addresses associated with a Token Ring map."
	INDEX { trnetMapSummaryNetID, trnetMapSummaryIndex }
	::= { trnetMapSummaryTable 1 }

TrnetMapSummaryEntry ::=
	SEQUENCE {
		trnetMapSummaryNetID
			INTEGER,
		trnetMapSummaryIndex
			INTEGER,
		trnetMapSummary32Stations
			OCTET STRING
		}

trnetMapSummaryNetID OBJECT-TYPE
	SYNTAX INTEGER {
		isolated(2),		-- corresponds to ifIndex
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		It can be isolated from the backplane, or on one of seven
		possible backplane token ring networks."
	::= { trnetMapSummaryEntry 1 }

trnetMapSummaryIndex OBJECT-TYPE
	SYNTAX INTEGER
	ACCESS read-only
	STATUS mandatory
	DESCRIPTION
		"The index into the map array. Possible values are 1 through 8.
		The MAC address of this agent is the first MAC address in
		trnetMapSummary32Stations indexed by a 1 in this entry."
	::= { trnetMapSummaryEntry 2 }

trnetMapSummary32Stations OBJECT-TYPE
	SYNTAX OCTET STRING (SIZE(8..256))
	ACCESS read-only
	STATUS mandatory
	DESCRIPTION
		"A concatonated group of MAC addresses and their associated
		slot and port of stations on the ring. Each entry has the
		eight octets. The first six octets are the MAC address.
		The seventh octet is the slot ID (or 255 if it is external
		to the concentrator). The eighth is the port ID (or 255
		if it is external to the concentrator).
		The MAC addresses are in the same order as the token flow."
	::= { trnetMapSummaryEntry 3 }


--
--  Network Traffic
--

trTrafTable OBJECT-TYPE
    SYNTAX SEQUENCE OF TrTrafEntry
    ACCESS not-accessible
    STATUS mandatory
    DESCRIPTION
	"A list of Token Ring network traffic (non-error) statistics entries.
	Note that all of the frame and octet counters in this table
	include error frames that have valid length;
	all octet counters exclude framing bits but include FCS octets."
    ::= { trnet 6 }

trTrafEntry OBJECT-TYPE
    SYNTAX TrTrafEntry
    ACCESS not-accessible
    STATUS mandatory
    DESCRIPTION
	"A collection of statistics kept for a particular
	Token Ring interface.
	Note that all of the frame and octet counters in this table
	include error frames that have valid length;
	all octet counters exclude framing bits but include FCS octets."
    INDEX { trTrafNetID }
    ::= { trTrafTable 1 }

TrTrafEntry ::= SEQUENCE {
  trTrafNetID			INTEGER,
  trTrafTokenRotationTime	INTEGER,
  trTrafDropEvents		Counter,
  trTrafOctets		Counter,
  trTrafFrames		Counter,
  trTrafMacOctets		Counter,
  trTrafMacFrames		Counter,
  trTrafBroadcastFrames Counter,
  trTrafMulticastFrames Counter,
  trTrafFrames18to63Octets    Counter,
  trTrafFrames64to127Octets   Counter,
  trTrafFrames128to255Octets  Counter,
  trTrafFrames256to511Octets  Counter,
  trTrafFrames512to1023Octets Counter,
  trTrafFrames1024to2047Octets Counter,
  trTrafFrames2048to4095Octets Counter,
  trTrafFrames4096to8191Octets Counter,
  trTrafFrames8192to18000Octets Counter,
  trTrafFramesGreaterThan18000Octets	Counter
}

trTrafNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trTrafEntry 1 }

trTrafTokenRotationTime OBJECT-TYPE
    SYNTAX INTEGER
    ACCESS read-only
    STATUS mandatory
    DESCRIPTION
	"An estimate of the time (in microseconds) that it takes for the
	token to complete a single rotation around the ring."
    ::= { trTrafEntry 2 }

trTrafDropEvents OBJECT-TYPE
    SYNTAX Counter
    ACCESS read-only
    STATUS mandatory
    DESCRIPTION
	"The total number of events in which frames
	were dropped by the TRMM due to lack of resources.
	Note that this number is not necessarily the number of
	frames dropped; it is just the number of times this
	condition has been detected."
    ::= { trTrafEntry 3 }

trTrafOctets OBJECT-TYPE
    SYNTAX Counter
    ACCESS read-only
    STATUS mandatory
    DESCRIPTION
	"The total number of octets of data received on the network."
    ::= { trTrafEntry 4 }

trTrafFrames OBJECT-TYPE
    SYNTAX Counter
    ACCESS read-only
    STATUS mandatory
    DESCRIPTION
	"The total number of frames received."
    ::= { trTrafEntry 5 }

trTrafMacOctets OBJECT-TYPE
    SYNTAX Counter
    ACCESS read-only
    STATUS mandatory
    DESCRIPTION
	"The total number of octets of data in MAC frames
	received on the network."
    ::= { trTrafEntry 6 }

trTrafMacFrames OBJECT-TYPE
    SYNTAX Counter
    ACCESS read-only
    STATUS mandatory
    DESCRIPTION
	"The total number of MAC frames received."
    ::= { trTrafEntry 7 }

trTrafBroadcastFrames OBJECT-TYPE
    SYNTAX Counter
    ACCESS read-only
    STATUS mandatory
    DESCRIPTION
	"The total number of non-MAC frames received that were
	directed to a broadcast address (0xFFFFFFFFFFFF or 0xC000FFFFFFFF)."
    ::= { trTrafEntry 8 }

trTrafMulticastFrames OBJECT-TYPE
    SYNTAX Counter
    ACCESS read-only
    STATUS mandatory
    DESCRIPTION
	"The total number of non-MAC frames received that were
	directed to a local or global multicast or functional address.
	Note that this number does not include frames directed to
	a broadcast address."
    ::= { trTrafEntry 9 }

trTrafFrames18to63Octets OBJECT-TYPE
    SYNTAX Counter
    ACCESS read-only
    STATUS mandatory
    DESCRIPTION
	"The total number of non-MAC frames received that were between
	18 and 63 octets in length inclusive."
    ::= { trTrafEntry 10 }

trTrafFrames64to127Octets OBJECT-TYPE
    SYNTAX Counter
    ACCESS read-only
    STATUS mandatory
    DESCRIPTION
	"The total number of non-MAC frames received that were between
	64 and 127 octets in length inclusive."
    ::= { trTrafEntry 11 }

trTrafFrames128to255Octets OBJECT-TYPE
    SYNTAX Counter
    ACCESS read-only
    STATUS mandatory
    DESCRIPTION
	"The total number of non-MAC frames received that were between
	128 and 255 octets in length inclusive."
    ::= { trTrafEntry 12 }

trTrafFrames256to511Octets OBJECT-TYPE
    SYNTAX Counter
    ACCESS read-only
    STATUS mandatory
    DESCRIPTION
	"The total number of non-MAC frames received that were between
	256 and 511 octets in length inclusive."
    ::= { trTrafEntry 13 }

trTrafFrames512to1023Octets OBJECT-TYPE
    SYNTAX Counter
    ACCESS read-only
    STATUS mandatory
    DESCRIPTION
	"The total number of non-MAC frames received that were between
	512 and 1023 octets in length inclusive."
    ::= { trTrafEntry 14 }

trTrafFrames1024to2047Octets OBJECT-TYPE
    SYNTAX Counter
    ACCESS read-only
    STATUS mandatory
    DESCRIPTION
	"The total number of non-MAC frames received that were between
	1024 and 2047 octets in length inclusive."
    ::= { trTrafEntry 15 }

trTrafFrames2048to4095Octets OBJECT-TYPE
    SYNTAX Counter
    ACCESS read-only
    STATUS mandatory
    DESCRIPTION
	"The total number of non-MAC frames received that were between
	2048 and 4095 octets in length inclusive."
    ::= { trTrafEntry 16 }

trTrafFrames4096to8191Octets OBJECT-TYPE
    SYNTAX Counter
    ACCESS read-only
    STATUS mandatory
    DESCRIPTION
	"The total number of non-MAC frames received that were between
	4096 and 8191 octets in length inclusive."
    ::= { trTrafEntry 17 }

trTrafFrames8192to18000Octets OBJECT-TYPE
    SYNTAX Counter
    ACCESS read-only
    STATUS mandatory
    DESCRIPTION
	"The total number of non-MAC frames received that were between
	8192 and 18000 octets in length inclusive."
    ::= { trTrafEntry 18 }

trTrafFramesGreaterThan18000Octets OBJECT-TYPE
    SYNTAX Counter
    ACCESS read-only
    STATUS mandatory
    DESCRIPTION
	"The total number of non-MAC frames received that were
	greater than or equal to 18000 octets in length."
    ::= { trTrafEntry 19 }


-- Station and Port Traffic


-- The TrTrafControl, TrTrafStation, TrTrafPort, TrTrafTopN, and
-- TrTrafTopNSummary Groups

--
-- New stations on the token ring network are discovered by
-- keeping a list of source and destination MAC Addresses seen
-- in good frames.  For each of these addresses, a set of statistics
-- is maintained.  The TrTrafStation, TrTrafPort, TrTrafTopN,
-- and TrTrafTopNSummary Groups provide four different ways
-- to retrieve this information.
--
-- Note that the list of stations will include
--	- stations internal to the concentrator on the local ring
--	- stations external to the concentrator on the local ring
--	- stations on remote rings
--
-- If the list is full, the least recently used entries not on the local ring
-- will be deleted first, as needed.

-- The trTrafStationTable contains entries for each address
-- discovered on a particular interface.  Each entry
-- contains statistical data about that station.  This table
-- is indexed by Network ID and the MAC address of the station.

-- The trTrafPortTable contains data in the same format as the
-- trTrafStationTable, and contains the same set of stations
-- except that stations external to the concentrator or not on the local ring
-- are omitted.  The trTrafPortTable is
-- indexed by Network ID, SlotIndex and PortIndex.

-- The trTrafTopNTable is composed of 7 sublists, one for each statistic.
-- Each sublist contains the same set of stations as
-- trTrafStationTable.  The stations in each sublist are sorted by
-- the statistic specified in trTrafTopNStatistic.
-- The trTrafTopNTable is indexed by trTrafTopNNetID,
-- by trTrafTopNStatistic to identify the sublist,
-- and by trTrafTopNIndex (1..N) with index 1 referring to
-- the entry with the highest value of the specifed counter.
-- (See description of trTrafTopNTable)

-- The trTrafTopNSummaryTable contains the same information as
-- trTrafTopNTable, but in a condensed format.

-- Note that table entries may be added, deleted, or resorted at any time.
-- There are three methods available for a management station to address this.

-- METHOD 1
-- Each of the 4 tables has an associated "-LastChangeTime" entry in
-- trTrafControlTable.  A management station should read the
-- associated "-LastChangeTime" entry before and after reading a group of
-- table entries.  If the before and after "-LastChangeTimes differ then the
-- management station should repeat the reading of table entries.

-- METHOD 2
-- Use trTrafControlLogicalLock and trTrafControlLogicalState to ensure
-- that changes don't occur while retrieving table entries.
-- (see description below)

-- METHOD 3
-- Don't worry about table entry changes.  Probably they won't happen while
-- you are reading the table.  The worst that would happen is you might miss
-- a few stations or see the same station twice in the list.


trTrafControlTable OBJECT-TYPE
    SYNTAX SEQUENCE OF TrTrafControlEntry
    ACCESS not-accessible
    STATUS mandatory
    DESCRIPTION
	"A list entries containing information about
	trTrafStationTable, trTrafPortTable, trTrafTopNTable, and
	trTrafTopNSummaryTable"
    ::= { trnet 7 }

trTrafControlEntry OBJECT-TYPE
    SYNTAX TrTrafControlEntry
    ACCESS not-accessible
    STATUS mandatory
    DESCRIPTION
	"A collection of information about
	trTrafStationTable, trTrafPortTable, trTrafTopNTable, and
	trTrafTopNSummaryTable"
    INDEX { trTrafControlNetID }
    ::= { trTrafControlTable 1 }

TrTrafControlEntry ::= SEQUENCE {
  trTrafControlNetID			INTEGER,
  trTrafControlLogicalState		INTEGER,
  trTrafControlLogicalLock		INTEGER,
  trTrafControlClear			INTEGER,
  trTrafControlLastClearTime		TimeTicks,
  trTrafControlTotalStations		INTEGER,
  trTrafControlStationLastChangeTime	TimeTicks,
  trTrafControlPortTotalStations	INTEGER,
  trTrafControlPortLastChangeTime	TimeTicks,
  trTrafControlTopNMaxStations  INTEGER,
  trTrafControlTopNTotalStations	INTEGER,
  trTrafControlTopNLastChangeTime	TimeTicks,
  trTrafControlTopNInterval		INTEGER
}

trTrafControlNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trTrafControlEntry 1 }

trTrafControlLogicalState OBJECT-TYPE
	SYNTAX INTEGER {
		changing(1),
		notChanging(2)
		}
	ACCESS read-only
	STATUS mandatory
	DESCRIPTION
		"The state of the token ring station traffic tables:
		trTrafStationTable, trTrafPortTable, trTrafTopNTable
		and trTrafTopNSummaryTable. If any of the tables associated
		with this trTrafControlEntry are being updated,
		then the state is changing(1)."
	::= { trTrafControlEntry 2 }

trTrafControlLogicalLock OBJECT-TYPE
	SYNTAX INTEGER {
		lock(1),
		unlock(2)
		}
	ACCESS read-write
	STATUS mandatory
	DESCRIPTION
		"A semaphore for locking the token ring station traffic
		tables: trTrafStationTable, trTrafPortTable,
		trTrafTopNTable, and trTrafTopNSummaryTable.
		When the semaphore is locked, adds, deletes, and re-sorting
		the traffic tables associated with this
		trTrafControlEntry will pend until the
		semaphore is unlocked, so that a valid set of entries
		can be read.  Note that the normal incrementing of the traffic
		counters are not affected by the setting of this semaphore.
		This cannot be set to unlock if trTrafControlLogicalState is
		changing.
		For complete accuracy, this semaphore
		should be read after being set to
		ensure that the tables were not changing when the lock was
		attempted. After the table information has been recorded,
		the semaphore should be set to unlock to allow changes to
		occur."
	::= { trTrafControlEntry 3 }


trTrafControlClear OBJECT-TYPE
  SYNTAX INTEGER {
	  normal(1),
	  clear(2)
  }
  ACCESS read-write
  STATUS mandatory
  DESCRIPTION
	"When the value of this object is set to clear,
	all entries in the token ring station traffic
	tables (trTrafStationTable, trTrafPortTable,
	trTrafTopNTable, and trTrafTopNSummaryTable) are cleared."
    ::= { trTrafControlEntry 4 }

trTrafControlLastClearTime OBJECT-TYPE
  SYNTAX TimeTicks
  ACCESS read-only
  STATUS mandatory
  DESCRIPTION
	"The value of sysUpTime when the token ring station traffic
	tables (trTrafStationTable, trTrafPortTable,
	trTrafTopNTable and trTrafTopNSummaryTable) were cleared.
	If never cleared, this value shall be zero (and the token ring
	station traffic tables will contain information collected since
	the XMM was started up)."
    ::= { trTrafControlEntry 5 }

trTrafControlTotalStations OBJECT-TYPE
  SYNTAX INTEGER
  ACCESS read-only
  STATUS mandatory
  DESCRIPTION
	"The number of stations in the portion of the trTrafStationTable
	associated with this trTrafControlEntry."
    ::= { trTrafControlEntry 6 }

trTrafControlStationLastChangeTime OBJECT-TYPE
  SYNTAX TimeTicks
  ACCESS read-only
  STATUS mandatory
  DESCRIPTION
      "The value of sysUpTime when the last entry
      was added to or deleted (or re-sorted)
      from the portion of the trTrafStationTable
      associated with this trTrafControlEntry.  If no
      additions or deletions have occurred, this value shall be zero."
    ::= { trTrafControlEntry 7 }

trTrafControlPortTotalStations OBJECT-TYPE
  SYNTAX INTEGER
  ACCESS read-only
  STATUS mandatory
  DESCRIPTION
	"The number of stations in the portion of the trTrafPortTable
	associated with this trTrafControlEntry."
    ::= { trTrafControlEntry 8 }

trTrafControlPortLastChangeTime OBJECT-TYPE
  SYNTAX TimeTicks
  ACCESS read-only
  STATUS mandatory
  DESCRIPTION
      "The value of sysUpTime when the last entry
      was added to or deleted (or re-sorted)
      from the portion of the trTrafPortTable
      associated with this trTrafControlEntry.  If no
      additions or deletions have occurred, this value shall be zero."
    ::= { trTrafControlEntry 9 }

trTrafControlTopNMaxStations OBJECT-TYPE
  SYNTAX INTEGER
  ACCESS read-write
  STATUS mandatory
  DESCRIPTION
	"Specifies a maximum value for trTrafControlTopNTotalStations
	in this trTrafControlEntry.  If this value is zero then no
	maximum value for trTrafControlTopNTotalStations is specified."
--	DEFVAL { 0 }
    ::= { trTrafControlEntry 10 }

trTrafControlTopNTotalStations OBJECT-TYPE
  SYNTAX INTEGER
  ACCESS read-only
  STATUS mandatory
  DESCRIPTION
	"The number of stations (for each statistic) in the portion of
	the trTrafTopNTable and trTrafTopNSummaryTable associated
	with this trTrafControlEntry.  If trTrafControlTopNMaxStations
	is zero or is not less than trTrafControlTotalStations then
	trTrafControlTopNTotalStations will have the same value as
	trTrafControlTotalStations.  Otherwise
	trTrafControlTopNTotalStations will
	have the same value as trTrafControlTopNMaxStations."
    ::= { trTrafControlEntry 11 }

trTrafControlTopNLastChangeTime OBJECT-TYPE
  SYNTAX TimeTicks
  ACCESS read-only
  STATUS mandatory
  DESCRIPTION
      "The value of sysUpTime when the last entry
      was added to or deleted (or re-sorted)
      from the portion of the trTrafTopNTable and trTrafTopNSummaryTable
      associated with this trTrafControlEntry.
      This is equivalent to the time when
      the last TopN data collection period ended.
      If no additions or deletions have occurred, this value shall be zero."
    ::= { trTrafControlEntry 12 }

trTrafControlTopNInterval OBJECT-TYPE
  SYNTAX INTEGER
  ACCESS read-write
  STATUS mandatory
  DESCRIPTION
      "Specifies the length of the TopN data collection period in seconds.
      Minimum length is 5 seconds; maximum is 86400 seconds (24 hours).
      When this value is modified, all associated entries in
      trTrafTopNTable and trTrafTopNSummaryTable are deleted and a new
      TopN data collection period is started."
--	DEFVAL {30}
    ::= { trTrafControlEntry 13 }


trTrafStationTable OBJECT-TYPE
  SYNTAX SEQUENCE OF TrTrafStationEntry
  ACCESS not-accessible
  STATUS mandatory
  DESCRIPTION
      "A list of Token Ring station traffic statistics entries
      indexed by Network ID and MAC address.  The table has
      trTrafTotalStations entries.
	Note that all of the frame and octet counters in this table
	include error frames that have valid length;
	all octet counters exclude framing bits but include FCS octets."
  ::= { trnet 8 }

trTrafStationEntry OBJECT-TYPE
  SYNTAX TrTrafStationEntry
  ACCESS not-accessible
  STATUS mandatory
  DESCRIPTION
      "A collection of station statistics for a particular station
      that has been discovered on an interface of this
      device.
	Note that all of the frame and octet counters in this table
	include error frames that have valid length;
	all octet counters exclude framing bits but include FCS octets."
  INDEX { trTrafStationNetID,
		trTrafStationAddress }
  ::= { trTrafStationTable 1 }

TrTrafStationEntry ::= SEQUENCE {
  trTrafStationNetID			INTEGER,
  trTrafStationAddress		MacAddress,
  trTrafStationSlotIndex		INTEGER,
  trTrafStationPortIndex		INTEGER,
  trTrafStationInFrames		Counter,
  trTrafStationOutFrames		Counter,
  trTrafStationInOctets		Counter,
  trTrafStationOutOctets		Counter,
  trTrafStationOutErrors		Counter,
  trTrafStationOutBroadcastFrames	Counter,
  trTrafStationOutMulticastFrames	Counter
}

trTrafStationNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trTrafStationEntry 1 }

trTrafStationAddress OBJECT-TYPE
  SYNTAX MacAddress
  ACCESS read-only
  STATUS mandatory
  DESCRIPTION
      "The physical address of this station."
  ::= { trTrafStationEntry 2 }

trTrafStationSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		remote-ring(254),
		external(255)
		}
	ACCESS read-only
	STATUS mandatory
	DESCRIPTION
		"The slot number of the station with this address.
		Addresses with a slot value of remote-ring(254) are
		not in this ring.
		Addresses with a slot value of external(255) are
		not in this concentrator."
  ::= { trTrafStationEntry 3 }

trTrafStationPortIndex OBJECT-TYPE
	SYNTAX INTEGER
	ACCESS read-only
	STATUS mandatory
	DESCRIPTION
		"The port number within trTrafSlotIndex's
		slot that received this address.
		If trTrafSlotIndex has a value of
		remote-ring(254), then the port address will be 254.
		If trTrafSlotIndex has a value of
		external(255), then the port address will be 255."
  ::= { trTrafStationEntry 4 }

trTrafStationInFrames OBJECT-TYPE
  SYNTAX Counter
  ACCESS read-only
  STATUS mandatory
  DESCRIPTION
      "The number of frames transmitted to this address since it was
      added to this table."
  ::= { trTrafStationEntry 5 }

trTrafStationOutFrames OBJECT-TYPE
  SYNTAX Counter
  ACCESS read-only
  STATUS mandatory
  DESCRIPTION
      "The number of frames transmitted by this address since it was
      added to this table."
  ::= { trTrafStationEntry 6 }

trTrafStationInOctets OBJECT-TYPE
  SYNTAX Counter
  ACCESS read-only
  STATUS mandatory
  DESCRIPTION
      "The number of octets transmitted to this address since it was
      added to this table."
  ::= { trTrafStationEntry 7 }

trTrafStationOutOctets OBJECT-TYPE
  SYNTAX Counter
  ACCESS read-only
  STATUS mandatory
  DESCRIPTION
      "The number of octets transmitted by this address since it was
      added to this table."
  ::= { trTrafStationEntry 8 }

trTrafStationOutErrors OBJECT-TYPE
  SYNTAX Counter
  ACCESS read-only
  STATUS mandatory
  DESCRIPTION
      "The number of error frames transmitted by this
      address since it was added to this table.  Only isolating errors
      (LineErrors, BurstErrors, ACErrors, InternalErrors, and AbortErrors)
      and CongestionErrors are counted."
  ::= { trTrafStationEntry 9 }

trTrafStationOutBroadcastFrames OBJECT-TYPE
  SYNTAX Counter
  ACCESS read-only
  STATUS mandatory
  DESCRIPTION
      "The number of frames transmitted by this address
      that were directed to the broadcast address since it was
      added to this table."
  ::= { trTrafStationEntry 10 }

trTrafStationOutMulticastFrames OBJECT-TYPE
  SYNTAX Counter
  ACCESS read-only
  STATUS mandatory
  DESCRIPTION
      "The number of frames transmitted by this address
      that were directed to a multicast address since it was
      added to this table.
      Note that this number does not include frames
      directed to the broadcast address."
  ::= { trTrafStationEntry 11 }


trTrafPortTable OBJECT-TYPE
  SYNTAX SEQUENCE OF TrTrafPortEntry
  ACCESS not-accessible
  STATUS mandatory
  DESCRIPTION
      "A list of Token Ring station traffic statistics entries
      indexed by slot number, and port number.  Note that stations external
      to this concentrator or on another ring are excluded from this table.
	Note that all of the frame and octet counters in this table
	include error frames that have valid length;
	all octet counters exclude framing bits but include FCS octets."
  ::= { trnet 9 }

trTrafPortEntry OBJECT-TYPE
  SYNTAX TrTrafPortEntry
  ACCESS not-accessible
  STATUS mandatory
  DESCRIPTION
      "A collection of station statistics for a particular station
      that has been discovered on an interface of this
      device.
	Note that all of the frame and octet counters in this table
	include error frames that have valid length;
	all octet counters exclude framing bits but include FCS octets.
	include error frames; all octet counters exclude framing bits
	but include FCS octets."
  INDEX { trTrafPortSlotIndex, trTrafPortPortIndex }
  ::= { trTrafPortTable 1 }

TrTrafPortEntry ::= SEQUENCE {
  trTrafPortSlotIndex		INTEGER,
  trTrafPortPortIndex		INTEGER,
  trTrafPortNetID		INTEGER,
  trTrafPortAddress		MacAddress,
  trTrafPortInFrames		  Counter,
  trTrafPortOutFrames		  Counter,
  trTrafPortInOctets		Counter,
  trTrafPortOutOctets		Counter,
  trTrafPortOutErrors		Counter,
  trTrafPortOutBroadcastFrames    Counter,
  trTrafPortOutMulticastFrames    Counter
}

trTrafPortSlotIndex OBJECT-TYPE
	SYNTAX INTEGER
	ACCESS read-only
	STATUS mandatory
	DESCRIPTION
		"The slot number of the station with this address."
  ::= { trTrafPortEntry 1 }

trTrafPortPortIndex OBJECT-TYPE
	SYNTAX INTEGER
	ACCESS read-only
	STATUS mandatory
	DESCRIPTION
		"The port number within trTrafPortSlotIndex's
		slot that received this address."
  ::= { trTrafPortEntry 2 }

trTrafPortNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trTrafPortEntry 3 }

trTrafPortAddress OBJECT-TYPE
  SYNTAX MacAddress
  ACCESS read-only
  STATUS mandatory
  DESCRIPTION
      "The physical address of this station."
  ::= { trTrafPortEntry 4 }

trTrafPortInFrames OBJECT-TYPE
  SYNTAX Counter
  ACCESS read-only
  STATUS mandatory
  DESCRIPTION
      "The number of frames transmitted to this address since it was
      added to this table."
  ::= { trTrafPortEntry 5 }

trTrafPortOutFrames OBJECT-TYPE
  SYNTAX Counter
  ACCESS read-only
  STATUS mandatory
  DESCRIPTION
      "The number of frames transmitted by this address since it was
      added to this table."
  ::= { trTrafPortEntry 6 }

trTrafPortInOctets OBJECT-TYPE
  SYNTAX Counter
  ACCESS read-only
  STATUS mandatory
  DESCRIPTION
      "The number of octets transmitted to this address since it was
      added to this table."
  ::= { trTrafPortEntry 7 }

trTrafPortOutOctets OBJECT-TYPE
  SYNTAX Counter
  ACCESS read-only
  STATUS mandatory
  DESCRIPTION
      "The number of octets transmitted by this address since it was
      added to this table."
  ::= { trTrafPortEntry 8 }

trTrafPortOutErrors OBJECT-TYPE
  SYNTAX Counter
  ACCESS read-only
  STATUS mandatory
  DESCRIPTION
      "The number of error frames transmitted by this
      address since it was added to this table.  Only isolating errors
      (LineErrors, BurstErrors, ACErrors, InternalErrors, and AbortErrors)
      and CongestionErrors are counted."
  ::= { trTrafPortEntry 9 }

trTrafPortOutBroadcastFrames OBJECT-TYPE
  SYNTAX Counter
  ACCESS read-only
  STATUS mandatory
  DESCRIPTION
      "The number of frames transmitted by this address
      that were directed to the broadcast address since it was
      added to this table."
  ::= { trTrafPortEntry 10 }

trTrafPortOutMulticastFrames OBJECT-TYPE
  SYNTAX Counter
  ACCESS read-only
  STATUS mandatory
  DESCRIPTION
      "The number of frames transmitted by this address
      that were directed to a multicast address since it was
      added to this table.
      Note that this number does not include frames
      directed to the broadcast address."
  ::= { trTrafPortEntry 11 }


trTrafTopNTable OBJECT-TYPE
  SYNTAX SEQUENCE OF TrTrafTopNEntry
  ACCESS not-accessible
  STATUS mandatory
  DESCRIPTION
      "A list of Token Ring station traffic statistics entries indexed by
	trTrafTopNNetID, trTrafTopNStatistic, and trTrafTopNIndex.
	For each Network, the list contains 7 logical sublists - one for
	each statistic.
	Each of the sublists has trTrafControlTopNTotalStations entries.
	For eack Network, the table has 7 times
	trTrafTopNControlTotalStations entries.
	All of the counters in this table reflect activity during the last
	completed TopN data collection period
	(trTrafControlTopNInterval seconds).
	Note that this table will contain no entries
	if a TopN data collection period has not yet completed since
	trTrafControlTopNInterval was modified or since startup.
	Note that all of the frame and octet counters in this table
	include error frames that have valid length;
	all octet counters exclude framing bits but include FCS octets."
  ::= { trnet 10 }

trTrafTopNEntry OBJECT-TYPE
  SYNTAX TrTrafTopNEntry
  ACCESS not-accessible
  STATUS mandatory
  DESCRIPTION
      "A collection of station statistics for a particular station
      that has been discovered on an interface of this
      device.
	Note that all of the frame and octet counters in this table
	include error frames that have valid length;
	all octet counters exclude framing bits but include FCS octets."
  INDEX { trTrafTopNNetID,
		trTrafTopNStatistic,
		trTrafTopNIndex }
  ::= { trTrafTopNTable 1 }

TrTrafTopNEntry ::= SEQUENCE {
  trTrafTopNNetID		INTEGER,
  trTrafTopNStatistic		  INTEGER,
  trTrafTopNIndex		INTEGER,
  trTrafTopNAddress		MacAddress,
  trTrafTopNSlotIndex		INTEGER,
  trTrafTopNPortIndex		INTEGER,
  trTrafTopNInFrames		  Counter,
  trTrafTopNOutFrames		  Counter,
  trTrafTopNInOctets		Counter,
  trTrafTopNOutOctets		Counter,
  trTrafTopNOutErrors		Counter,
  trTrafTopNOutBroadcastFrames    Counter,
  trTrafTopNOutMulticastFrames    Counter
}

trTrafTopNNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trTrafTopNEntry 1 }

trTrafTopNStatistic OBJECT-TYPE
  SYNTAX INTEGER {
	  trTrafTopNInFrames(1),
	  trTrafTopNOutFrames(2),
	  trTrafTopNInOctets(3),
	  trTrafTopNOutOctets(4),
	  trTrafTopNOutErrors(5),
	  trTrafTopNOutBroadcastFrames(6),
	  trTrafTopNOutMulticastFrames(7)
  }
  ACCESS read-only
  STATUS mandatory
  DESCRIPTION
      "The object representing the statistic for each station that this
      portion of the trTrafTopNTable is sorted on."
    ::= { trTrafTopNEntry 2 }

trTrafTopNIndex OBJECT-TYPE
  SYNTAX INTEGER
  ACCESS read-only
  STATUS mandatory
  DESCRIPTION
      "An index that uniquely identifies an entry in
      the trTrafTopN table among those in the same network
      and for the same trTrafTopNStatistic.
      This index is between 1 and N, where N is the value of
      trTrafControlTopNTotalStations.  Increasing values
      of trTrafTopNIndex shall be assigned to entries with
      decreasing values of the object referenced by trTrafTopNStatistic."
  ::= { trTrafTopNEntry 3 }

trTrafTopNAddress OBJECT-TYPE
  SYNTAX MacAddress
  ACCESS read-only
  STATUS mandatory
  DESCRIPTION
      "The physical address of this station."
  ::= { trTrafTopNEntry 4 }

trTrafTopNSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		remote-ring(254),
		external(255)
		}
	ACCESS read-only
	STATUS mandatory
	DESCRIPTION
		"The slot number of the station with this address.
		Addresses with a slot value of remote-ring(254) are
		not in this ring.
		Addresses with a slot value of external(255) are
		not in this concentrator."
  ::= { trTrafTopNEntry 5 }

trTrafTopNPortIndex OBJECT-TYPE
	SYNTAX INTEGER
	ACCESS read-only
	STATUS mandatory
	DESCRIPTION
		"The port number within trTrafTopNSlotIndex's
		slot that received this address.
		If trTrafTopNSlotIndex has a value of
		remote-ring(254), then the port address will be 254.
		If trTrafTopNSlotIndex has a value of
		external(255), then the port address will be 255."
  ::= { trTrafTopNEntry 6 }

trTrafTopNInFrames OBJECT-TYPE
  SYNTAX Counter
  ACCESS read-only
  STATUS mandatory
  DESCRIPTION
      "The number of frames transmitted to this address
      during the last TopN data collection period."
  ::= { trTrafTopNEntry 7 }

trTrafTopNOutFrames OBJECT-TYPE
  SYNTAX Counter
  ACCESS read-only
  STATUS mandatory
  DESCRIPTION
      "The number of frames transmitted by this address
      during the last TopN data collection period."
  ::= { trTrafTopNEntry 8 }

trTrafTopNInOctets OBJECT-TYPE
  SYNTAX Counter
  ACCESS read-only
  STATUS mandatory
  DESCRIPTION
      "The number of octets transmitted to this address
      during the last TopN data collection period."
  ::= { trTrafTopNEntry 9 }

trTrafTopNOutOctets OBJECT-TYPE
  SYNTAX Counter
  ACCESS read-only
  STATUS mandatory
  DESCRIPTION
      "The number of octets transmitted by this address
      during the last TopN data collection period."
  ::= { trTrafTopNEntry 10 }

trTrafTopNOutErrors OBJECT-TYPE
  SYNTAX Counter
  ACCESS read-only
  STATUS mandatory
  DESCRIPTION
      "The number of error frames transmitted by this address
      during the last TopN data collection period.  Only isolating errors
      (LineErrors, BurstErrors, ACErrors, InternalErrors, and AbortErrors)
      and CongestionErrors are counted."
  ::= { trTrafTopNEntry 11 }

trTrafTopNOutBroadcastFrames OBJECT-TYPE
  SYNTAX Counter
  ACCESS read-only
  STATUS mandatory
  DESCRIPTION
      "The number of frames transmitted by this address
      that were directed to the broadcast address
      during the last TopN data collection period."
  ::= { trTrafTopNEntry 12 }

trTrafTopNOutMulticastFrames OBJECT-TYPE
  SYNTAX Counter
  ACCESS read-only
  STATUS mandatory
  DESCRIPTION
      "The number of frames transmitted by this address
      that were directed to a multicast address
      during the last TopN data collection period.
      Note that this number does not include frames
      directed to the broadcast address."
  ::= { trTrafTopNEntry 13 }


trTrafTopNSummaryTable OBJECT-TYPE
  SYNTAX SEQUENCE OF TrTrafTopNSummaryEntry
  ACCESS not-accessible
  STATUS mandatory
  DESCRIPTION
      "A list containing information from trTrafTopNTable
	provided for the convenience of network management stations
	that wish to obtain this information in condensed form."
  ::= { trnet 11 }

trTrafTopNSummaryEntry OBJECT-TYPE
  SYNTAX TrTrafTopNSummaryEntry
  ACCESS not-accessible
  STATUS mandatory
  DESCRIPTION
      "A segment of the Top N list for a particular statistic."
  INDEX { trTrafTopNSummaryNetID,
		trTrafTopNSummaryStatistic,
		trTrafTopNSummaryIndex }
  ::= { trTrafTopNSummaryTable 1 }

TrTrafTopNSummaryEntry ::= SEQUENCE {
  trTrafTopNSummaryNetID	       INTEGER,
  trTrafTopNSummaryStatistic		  INTEGER,
  trTrafTopNSummaryIndex	       INTEGER,
  trTrafTopNSummaryStations		OCTET STRING
}

trTrafTopNSummaryNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { trTrafTopNSummaryEntry 1 }

trTrafTopNSummaryStatistic OBJECT-TYPE
  SYNTAX INTEGER {
	  trTrafTopNSummaryInFrames(1),
	  trTrafTopNSummaryOutFrames(2),
	  trTrafTopNSummaryInOctets(3),
	  trTrafTopNSummaryOutOctets(4),
	  trTrafTopNSummaryOutErrors(5),
	  trTrafTopNSummaryOutBroadcastFrames(6),
	  trTrafTopNSummaryOutMulticastFrames(7)
  }
  ACCESS read-only
  STATUS mandatory
  DESCRIPTION
      "The object representing the statistic for each station that this
      portion of the trTrafTopNSummaryTable is sorted on."
    ::= { trTrafTopNSummaryEntry 2 }

trTrafTopNSummaryIndex OBJECT-TYPE
  SYNTAX INTEGER
  ACCESS read-only
  STATUS mandatory
  DESCRIPTION
	"An index that uniquely identifies an entry in
	the trTrafTopNSummary table among those in the same network
	and for the same trTrafTopNSummaryStatistic.
	The number of entries for this portion of trTrafTopNSummaryTable
	is number of entries for the corresponding portion of
	trTrafTopNTable divided by 12 (rounded up to the next integer)."
  ::= { trTrafTopNSummaryEntry 3 }

trTrafTopNSummaryStations OBJECT-TYPE
	SYNTAX OCTET STRING
	ACCESS read-only
	STATUS mandatory
	DESCRIPTION
		"A concatonated list of (up to 12) MAC addresses,
		their associated slot and port, and a statistic value
		for traffic associated with stations on the ring.  Each entry
		has 36 octets. The first 6 octets are the MAC address.
		The 7th octet is the slot ID (or 255 if it is external
		to the concentrator or 254 if it is on a remote ring).
		The 8th is the port ID (or 255 if it is external to the
		concentrator or 254 if it is on a remote ring).
		The 9th through 36th octets contain the values of the
		statistics trTrafTopNInFrames, trTrafTopNOutFrames,
		trTrafTopNInOctets, trTrafTopNOutOctets,
		trTrafTopNOutErrors, trTrafTopNOutBroadcastFrames,
		and trTrafTopNOutMulticastFrames.  Each statistic is
		represented in 4 octets, most significant octet first.
		The stations are in order of decreasing values of the
		statistic referenced by trTrafTopNStatistic."
	::= { trTrafTopNSummaryEntry 4 }


-- The fddinet Group

fddiStatsModTable OBJECT-TYPE
	SYNTAX SEQUENCE OF FddiStatsModEntry
	ACCESS not-accessible
	STATUS mandatory
	DESCRIPTION
		"A table of statistical information counted for each module
		in each FDDI network."
	::= { fddinet 2 }

fddiStatsModEntry OBJECT-TYPE
	SYNTAX FddiStatsModEntry
	ACCESS not-accessible
	STATUS mandatory
	DESCRIPTION
		"A list of statistical information for each module
		on each FDDI network in the concentrator."
	INDEX { fddiStatsModSlotIndex }
	::= { fddiStatsModTable 1 }

FddiStatsModEntry ::=
	SEQUENCE {
		fddiStatsModSlotIndex
			INTEGER,
		fddiStatsModMgtRcvErrs
			Counter,
		fddiStatsModMgtXmitErrs
			Counter,
		fddiStatsModBackplaneErrs
			Counter,
		fddiStatsModPllUnlockErrs
			Counter
		}

fddiStatsModSlotIndex OBJECT-TYPE
	SYNTAX INTEGER
	ACCESS read-only
	STATUS mandatory
	DESCRIPTION
		"The slot number that contains this module."
	::= { fddiStatsModEntry 1 }

fddiStatsModMgtRcvErrs OBJECT-TYPE
	SYNTAX Counter
	ACCESS read-only
	STATUS mandatory
	DESCRIPTION
		"The number of errors encountered while receiving data
		 on the Management Channel."
	::= { fddiStatsModEntry 2 }

fddiStatsModMgtXmitErrs OBJECT-TYPE
	SYNTAX Counter
	ACCESS read-only
	STATUS mandatory
	DESCRIPTION
		"The number of errors encountered while transmitting data
		 on the Management Channel."
	::= { fddiStatsModEntry 3 }

fddiStatsModBackplaneErrs OBJECT-TYPE
	SYNTAX Counter
	ACCESS read-only
	STATUS mandatory
	DESCRIPTION
		"The number of errors while receiving and transmitting
		 network data on the backplane."
	::= { fddiStatsModEntry 4 }

fddiStatsModPllUnlockErrs OBJECT-TYPE
	SYNTAX Counter
	ACCESS read-only
	STATUS mandatory
	DESCRIPTION
		"The number of times the phased lock loop on the
		 backplane network data channel was lost."
	::= { fddiStatsModEntry 5 }


-- Port table

fddiStatsPortTable OBJECT-TYPE
	SYNTAX SEQUENCE OF FddiStatsPortEntry
	ACCESS not-accessible
	STATUS mandatory
	DESCRIPTION
		"A table of statistical information counted for each Port
		in each FDDI network."
	::= { fddinet 3 }

fddiStatsPortEntry OBJECT-TYPE
	SYNTAX FddiStatsPortEntry
	ACCESS not-accessible
	STATUS mandatory
	DESCRIPTION
		"A list of statistical information for each Port
		on each FDDI network in the concentrator."
	INDEX { fddiStatsPortSlotIndex, fddiStatsPortIndex }
	::= { fddiStatsPortTable 1 }

FddiStatsPortEntry ::=
	SEQUENCE {
		fddiStatsPortSlotIndex
			INTEGER,
		fddiStatsPortIndex
			INTEGER,
		fddiStatsPortLCTFailCts
			Counter,
		fddiStatsPortLerEstimate
			INTEGER,
		fddiStatsPortLemRejectCts
			Counter,
		fddiStatsPortLemCts
			Counter
		}

fddiStatsPortSlotIndex OBJECT-TYPE
	SYNTAX INTEGER
	ACCESS read-only
	STATUS mandatory
	DESCRIPTION
		"The slot number that contains this Port."
	::= { fddiStatsPortEntry 1 }

fddiStatsPortIndex OBJECT-TYPE
	SYNTAX INTEGER
	ACCESS read-only
	STATUS mandatory
	DESCRIPTION
		"The Port number of this port"
	::= { fddiStatsPortEntry 2 }

fddiStatsPortLCTFailCts OBJECT-TYPE
	SYNTAX Counter
	ACCESS read-only
	STATUS mandatory
	DESCRIPTION
	   "The count of the consecutive times the link
	    confidence test (LCT) has failed during connection
	    management. Once the connection has been established,
	    the count is zeroed. (refer to ANSI 9.4.1)."
	::= { fddiStatsPortEntry 3 }

fddiStatsPortLerEstimate OBJECT-TYPE
	SYNTAX INTEGER
	ACCESS read-only
	STATUS mandatory
	DESCRIPTION
	    "A long term average link error rate.  It ranges
	     from 10**-4 to 10**-15 and is reported as the
	     absolute value of the exponent of the estimate
	     (the larger the number, the smaller the value)."
	::= { fddiStatsPortEntry 4 }

fddiStatsPortLemRejectCts OBJECT-TYPE
	SYNTAX Counter
	ACCESS read-only
	STATUS mandatory
	DESCRIPTION
	    "A link error monitoring count of the times that a
	     link has been removed from the ring due to the
	     LerCutOff threshold being exceeded."
	::= { fddiStatsPortEntry 5 }

fddiStatsPortLemCts OBJECT-TYPE
	SYNTAX Counter
	ACCESS read-only
	STATUS mandatory
	DESCRIPTION
	    "The aggregate link error monitor error count, set
	     to zero only on station power up. This variable's
	     long term rate average is lerEstimate."
	::= { fddiStatsPortEntry 6 }


fddinetStatsTable OBJECT-TYPE
	SYNTAX SEQUENCE OF FddinetStatsEntry
	ACCESS not-accessible
	STATUS mandatory
	DESCRIPTION
		"A table of statistical information counted for each FDDI
		network in the concentrator"
	::= { fddinet 4 }

fddinetStatsEntry OBJECT-TYPE
	SYNTAX FddinetStatsEntry
	ACCESS not-accessible
	STATUS mandatory
	DESCRIPTION
		"A list of statistical information for each FDDI
		network in the concentrator."
	INDEX { fddinetStatsNetID }
	::= { fddinetStatsTable 1 }

FddinetStatsEntry ::=
	SEQUENCE {
		fddinetStatsNetID
			INTEGER,
		fddinetStatsRingOpCounts
			Counter,
		fddinetStatsFrameCounts
			Counter,
		fddinetStatsErrorCounts
			Counter,
		fddinetStatsLostCounts
			Counter,
		fddinetStatsFrameErrorRatio
			INTEGER
	}

fddinetStatsNetID OBJECT-TYPE
	SYNTAX INTEGER {
		isolated(2),
		fddi-1(16),
		fddi-2(17),
		fddi-3(18),
		fddi-4(19)
		}
	ACCESS read-only
	STATUS mandatory
	DESCRIPTION
		"The network index that uniquely identifies this network.
		One of isolated, fddi-1, fddi-2, fddi-3, or fddi-4."
	::= { fddinetStatsEntry 1 }

fddinetStatsRingOpCounts OBJECT-TYPE
	SYNTAX Counter
	ACCESS read-only
	STATUS mandatory
	DESCRIPTION
		"The number times the ring transitioned to operational."
	::= { fddinetStatsEntry 2 }

fddinetStatsFrameCounts OBJECT-TYPE
	SYNTAX Counter
	ACCESS read-only
	STATUS mandatory
	DESCRIPTION
		"Frame_Ct (refer to ANSI MAC 2.2.1)."
	::= { fddinetStatsEntry 3 }

fddinetStatsErrorCounts OBJECT-TYPE
	SYNTAX Counter
	ACCESS read-only
	STATUS mandatory
	DESCRIPTION
		"Error_Ct (refer to ANSI MAC 2.2.1)."
	::= { fddinetStatsEntry 4 }

fddinetStatsLostCounts OBJECT-TYPE
	SYNTAX Counter
	ACCESS read-only
	STATUS mandatory
	DESCRIPTION
		"Lost_Ct (refer to ANSI MAC 2.2.1)."
	::= { fddinetStatsEntry 5 }

fddinetStatsFrameErrorRatio OBJECT-TYPE
	SYNTAX INTEGER (1..65535)
	ACCESS read-only
	STATUS mandatory
	DESCRIPTION
		"This attribute is the actual ratio, ((delta
		 snmpFddiMACLostCt + delta snmpFddiMACErrorCt) /
		 (delta snmpFddiMACFrameCt + delta
		 snmpFddiMACLostCt)) x 2**16."
	::= { fddinetStatsEntry 6 }




-- The Interface Table

-- This table contains state and parameter information which is
-- specific to 802.5 interfaces.  It is mandatory that systems
-- having 802.5 interfaces implement this table in addition to the
-- generic interfaces table [4,6] and its generic extensions [11].

dot5Table  OBJECT-TYPE
	SYNTAX  SEQUENCE OF Dot5Entry
	ACCESS  not-accessible
	STATUS  obsolete
	DESCRIPTION
		"This table contains Token Ring interface
		parameters and state variables, one entry
		per 802.5 interface."
	::= { dot5 1 }

dot5Entry  OBJECT-TYPE
	SYNTAX  Dot5Entry
	ACCESS  not-accessible
	STATUS  obsolete
	DESCRIPTION
		"A list of Token Ring status and parameter
		values for an 802.5 interface."
	INDEX	{ dot5IfIndex }
	::= { dot5Table 1 }

Dot5Entry ::=
	SEQUENCE {
	      dot5IfIndex
		  INTEGER,
	      dot5Commands
		  INTEGER,
	      dot5RingStatus
		  INTEGER,
	      dot5RingState
		  INTEGER,
	      dot5RingOpenStatus
		  INTEGER,
	      dot5RingSpeed
		  INTEGER,
	      dot5UpStream
		  MacAddress,
	      dot5ActMonParticipate
		  INTEGER,
	      dot5Functional
		  MacAddress
	  }

dot5IfIndex  OBJECT-TYPE
	SYNTAX  INTEGER
	ACCESS  read-only
	STATUS  obsolete
	DESCRIPTION
	     "The value of this object identifies the
	      802.5 interface for which this entry contains
	      management information.  The value of this
	      object for a particular interface has the same
	      value as the ifIndex object, defined in [4,6],
	      for the same interface."
	::= { dot5Entry 1 }

dot5Commands  OBJECT-TYPE
	SYNTAX  INTEGER {
		no-op(1),
		open(2),
		reset(3),
		close(4)
	}
	ACCESS  read-write
	STATUS  obsolete
	DESCRIPTION
		"   When this object is set to the value of open(2),
		the station should go into the open state.  The
		progress and success of the open is given by the
		values of the objects dot5RingState and
		dot5RingOpenStatus.
		    When this object is set to the value of
		reset(3), then the station should do a reset.
		On a reset, all MIB counters should retain their
		values, if possible.  Other side affects are
		dependent on the hardware chip set.
		    When this object is set to the value of
		close(4), the station should go into the stopped
		state by removing itself from the ring.
		Setting this object to a value of no-op(1)
		has no effect.
		    When read, this object always has a value
		of no-op(1)."
	::= { dot5Entry 2 }

dot5RingStatus OBJECT-TYPE
	SYNTAX  INTEGER
	ACCESS  read-only
	STATUS  obsolete
	DESCRIPTION
	     "   The current interface status which can be used
	     to diagnose fluctuating problems that can occur
	     on token rings, after a station has successfully
	     been added to the ring.
		 Before an open is completed, this object has
	     the value for the 'no status' condition.  The
	     dot5RingState and dot5RingOpenStatus objects
	     provide for debugging problems when the station
	     can not even enter the ring.
		 The object's value is a sum of values, one
	     for each currently applicable condition.  The
	     following values are defined for various
	     conditions:
		0 = No Problems detected
		32 = Ring Recovery
		64 = Single Station
		256 = Remove Received
		512 = reserved
		1024 = Auto-Removal Error
		2048 = Lobe Wire Fault
		4096 = Transmit Beacon
		8192 = Soft Error
		16384 = Hard Error
		32768 = Signal Loss
		131072 = no status, open not completed."
	::= { dot5Entry 3 }

dot5RingState  OBJECT-TYPE
	SYNTAX  INTEGER {
		opened(1),
		closed(2),
		opening(3),
		closing(4),
		openFailure(5),
		ringFailure(6)
	}
	ACCESS  read-only
	STATUS  obsolete
	DESCRIPTION
	     "The current interface state with respect to
	     entering or leaving the ring."
	::= { dot5Entry 4 }

dot5RingOpenStatus  OBJECT-TYPE
	SYNTAX  INTEGER {
		noOpen(1),     -- no open attempted
		badParam(2),
		lobeFailed(3),
		signalLoss(4),
		insertionTimeout(5),
		ringFailed(6),
		beaconing(7),
		duplicateMAC(8),
		requestFailed(9),
		removeReceived(10),
		open(11)      -- last open successful
	}
	ACCESS  read-only
	STATUS  obsolete
	DESCRIPTION
	     "This object indicates the success, or the
	     reason for failure, of the station's most
	     recent attempt to enter the ring."
	::= { dot5Entry 5 }

dot5RingSpeed  OBJECT-TYPE
	SYNTAX  INTEGER {
		unknown(1),
		oneMegabit(2),
		fourMegabit(3),
		sixteenMegabit(4)
	}
	ACCESS  read-write
	STATUS  obsolete
	DESCRIPTION
		"The ring's bandwidth."
	::= { dot5Entry 6 }

dot5UpStream  OBJECT-TYPE
	SYNTAX  MacAddress
	ACCESS  read-only
	STATUS  obsolete
	DESCRIPTION
	     "The MAC-address of the up stream neighbor
	      station in the ring."
	::= { dot5Entry 7 }

dot5ActMonParticipate OBJECT-TYPE
	SYNTAX  INTEGER {
		true(1),
		false(2)
	}
	ACCESS  read-write
	STATUS  obsolete
	DESCRIPTION
	     "If this object has a value of true(1) then
	     this interface will participate in the active
	     monitor selection process.  If the value is
	     false(2) then it will not.  Setting this
	     object might not have an effect until the
	     next time the interface is opened."
	::= { dot5Entry 8 }

dot5Functional OBJECT-TYPE
	SYNTAX  MacAddress
	ACCESS  read-write
	STATUS  obsolete
	DESCRIPTION
	     "The bit mask of all Token Ring functional
	     addresses for which this interface will
	     accept frames."
	::= { dot5Entry 9 }

--   The Statistics Table

-- This table contains statistics and error counter which are
-- specific to 802.5 interfaces.  It is mandatory that systems
-- having 802.5 interfaces implement this table.

dot5StatsTable  OBJECT-TYPE
	SYNTAX  SEQUENCE OF Dot5StatsEntry
	ACCESS  not-accessible
	STATUS  obsolete
	DESCRIPTION
	     "A table containing Token Ring statistics,
	     one entry per 802.5 interface.
		 All the statistics are defined using the
	     syntax Counter as 32-bit wrap around counters.
	     Thus, if an interface's hardware maintains these
	     statistics in 16-bit counters, then the agent
	     must read the hardware's counters frequently
	     enough to prevent loss of significance, in
	     order to maintain 32-bit counters in software."
	::= { dot5 2 }

dot5StatsEntry  OBJECT-TYPE
	SYNTAX  Dot5StatsEntry
	ACCESS  not-accessible
	STATUS  obsolete
	DESCRIPTION
	     "An entry contains the 802.5 statistics for a
	      particular interface."
	INDEX	{ dot5StatsIfIndex }
	::= { dot5StatsTable 1 }

Dot5StatsEntry ::=
	SEQUENCE {
	      dot5StatsIfIndex
		  INTEGER,
	      dot5StatsLineErrors
		  Counter,
	      dot5StatsBurstErrors
		  Counter,
	      dot5StatsACErrors
		  Counter,
	      dot5StatsAbortTransErrors
		  Counter,
	      dot5StatsInternalErrors
		  Counter,
	      dot5StatsLostFrameErrors
		  Counter,
	      dot5StatsReceiveCongestions
		  Counter,
	      dot5StatsFrameCopiedErrors
		  Counter,
	      dot5StatsTokenErrors
		  Counter,
	      dot5StatsSoftErrors
		  Counter,
	      dot5StatsHardErrors
		  Counter,
	      dot5StatsSignalLoss
		  Counter,
	      dot5StatsTransmitBeacons
		  Counter,
	      dot5StatsRecoverys
		  Counter,
	      dot5StatsLobeWires
		  Counter,
	      dot5StatsRemoves
		  Counter,
	      dot5StatsSingles
		  Counter,
	      dot5StatsFreqErrors
		  Counter
	  }

dot5StatsIfIndex  OBJECT-TYPE
	SYNTAX  INTEGER
	ACCESS  read-only
	STATUS  obsolete
	DESCRIPTION
	     "The value of this object identifies the
	     802.5 interface for which this entry contains
	     management information.  The value of this
	     object for a particular interface has the
	     same value as the ifIndex object, defined
	     in [4,6], for the same interface."
	::= { dot5StatsEntry 1 }

dot5StatsLineErrors OBJECT-TYPE
	SYNTAX  Counter
	ACCESS  read-only
	STATUS  obsolete
	DESCRIPTION
	     "This counter is incremented when a frame or
	     token is copied or repeated by a station, the
	     E bit is zero in the frame or token and one of
	     the following conditions exists: 1) there is a
	     non-data bit (J or K bit) between the SD and
	     the ED of the frame or token, or 2) there is an
	     FCS error in the frame."
	::= { dot5StatsEntry 2 }

dot5StatsBurstErrors OBJECT-TYPE
	SYNTAX  Counter
	ACCESS  read-only
	STATUS  obsolete
	DESCRIPTION
	     "This counter is incremented when a station
	     detects the absence of transitions for five
	     half-bit timers (burst-five error)."
	::= { dot5StatsEntry 3 }

dot5StatsACErrors OBJECT-TYPE
	SYNTAX  Counter
	ACCESS  read-only
	STATUS  obsolete
	DESCRIPTION
		"This counter is incremented when a station
		receives an AMP or SMP frame in which A is
		equal to C is equal to 0, and then receives
		another SMP frame with A is equal to C is
		equal to 0 without first receiving an AMP
		frame. It denotes a station that cannot set
		the AC bits properly."
		::= { dot5StatsEntry 4 }

dot5StatsAbortTransErrors OBJECT-TYPE
	SYNTAX  Counter
	ACCESS  read-only
	STATUS  obsolete
	DESCRIPTION
		"This counter is incremented when a station
		transmits an abort delimiter while transmitting."
		::= { dot5StatsEntry 5 }

dot5StatsInternalErrors OBJECT-TYPE
	SYNTAX  Counter
	ACCESS  read-only
	STATUS  obsolete
	DESCRIPTION
		"This counter is incremented when a station
		recognizes an internal error."
	::= { dot5StatsEntry 6 }

dot5StatsLostFrameErrors OBJECT-TYPE
	SYNTAX  Counter
	ACCESS  read-only
	STATUS  obsolete
	DESCRIPTION
		"This counter is incremented when a station
		is transmitting and its TRR timer expires.
		This condition denotes a condition where a
		transmitting station in strip mode does not
		receive the trailer of the frame before the
		TRR timer goes off."
	::= { dot5StatsEntry 7 }

dot5StatsReceiveCongestions OBJECT-TYPE
	SYNTAX  Counter
	ACCESS  read-only
	STATUS  obsolete
	DESCRIPTION
		"This counter is incremented when a station
		recognizes a frame addressed to its specific
		address, but has no available buffer space
		indicating that the station is congested."
	::= { dot5StatsEntry 8 }

dot5StatsFrameCopiedErrors OBJECT-TYPE
	SYNTAX  Counter
	ACCESS  read-only
	STATUS  obsolete
	DESCRIPTION
		"This counter is incremented when a station
		recognizes a frame addressed to its specific
		address and detects that the FS field A bits
		are set to 1 indicating a possible line hit
		or duplicate address."
	::= { dot5StatsEntry 9 }

dot5StatsTokenErrors OBJECT-TYPE
	SYNTAX  Counter
	ACCESS  read-only
	STATUS  obsolete
	DESCRIPTION
		"This counter is incremented when a station
		acting as the active monitor recognizes an
		error condition that needs a token transmitted."
	::= { dot5StatsEntry 10 }

dot5StatsSoftErrors OBJECT-TYPE
	SYNTAX  Counter
	ACCESS  read-only
	STATUS  obsolete
	DESCRIPTION
		"The number of Soft Errors the interface has
		detected. It directly corresponds to the number
		of Report Error MAC frames that this interface
		has transmitted. Soft Errors are those which are
		recoverable by the MAC layer protocols."
	::= { dot5StatsEntry 11 }

dot5StatsHardErrors OBJECT-TYPE
	SYNTAX  Counter
	ACCESS  read-only
	STATUS  obsolete
	DESCRIPTION
		"The number of times this interface has
		detected an immediately recoverable fatal error.
		It denotes the number of times this interface
		is either transmitting or receiving beacon
		MAC frames."
	::= { dot5StatsEntry 12 }

dot5StatsSignalLoss OBJECT-TYPE
	SYNTAX  Counter
	ACCESS  read-only
	STATUS  obsolete
	DESCRIPTION
		"The number of times this interface has
		detected the loss of signal condition from
		the ring."
	::= { dot5StatsEntry 13 }

dot5StatsTransmitBeacons OBJECT-TYPE
	SYNTAX  Counter
	ACCESS  read-only
	STATUS  obsolete
	DESCRIPTION
		"The number of times this interface has
		transmitted a beacon frame."
	::= { dot5StatsEntry 14 }

dot5StatsRecoverys OBJECT-TYPE
	SYNTAX  Counter
	ACCESS  read-only
	STATUS  obsolete
	DESCRIPTION
		"The number of Claim Token MAC frames
		received or transmitted after the interface
		has received a Ring Purge MAC frame. This
		counter signifies the number of times the
		ring has been purged and is being recovered
		back into a normal operating state."
	::= { dot5StatsEntry 15 }

dot5StatsLobeWires OBJECT-TYPE
	SYNTAX  Counter
	ACCESS  read-only
	STATUS  obsolete
	DESCRIPTION
		"The number of times the interface has
		detected an open or short circuit in the
		lobe data path. The adapter will be closed
		and dot5RingState will signify this condition."
	::= { dot5StatsEntry 16 }

dot5StatsRemoves OBJECT-TYPE
	SYNTAX  Counter
	ACCESS  read-only
	STATUS  obsolete
	DESCRIPTION
		"The number of times the interface has received
		a Remove Ring Station MAC frame request. When
		this frame is received the interface will enter
		the close state and dot5RingState will signify
		this condition."
	::= { dot5StatsEntry 17 }

dot5StatsSingles OBJECT-TYPE
	SYNTAX  Counter
	ACCESS  read-only
	STATUS  obsolete
	DESCRIPTION
		"The number of times the interface has sensed
		that it is the only station on the ring. This
		will happen if the interface is the first one
		up on a ring, or if there is a hardware problem."
	::= { dot5StatsEntry 18 }

dot5StatsFreqErrors OBJECT-TYPE
	SYNTAX  Counter
	ACCESS  read-only
	STATUS  obsolete
	DESCRIPTION
		"The number of times the interface has detected
		that the frequency of the incoming signal differs
		from the expected frequency by more than that
		ispecified by the IEEE 802.5 standard, see
		chapter 7 in [10]."
	::= { dot5StatsEntry 19 }


-- The Timer Table

-- This group contains the values of the timers defined in [10]
-- for 802.5 interfaces.  It is optional that systems having 802.5
-- interfaces implement this group.

dot5TimerTable  OBJECT-TYPE
	SYNTAX  SEQUENCE OF Dot5TimerEntry
	ACCESS  not-accessible
	STATUS  obsolete
	DESCRIPTION
		"This table contains Token Ring interface
		timer values, one entry per 802.5 interface."
	::= { dot5 5 }

dot5TimerEntry  OBJECT-TYPE
	SYNTAX  Dot5TimerEntry
	ACCESS  not-accessible
	STATUS  obsolete
	DESCRIPTION
		"A list of Token Ring timer values for an 802.5
		interface."
	INDEX	{ dot5TimerIfIndex }
	::= { dot5TimerTable 1 }

Dot5TimerEntry ::=
	SEQUENCE {
		dot5TimerIfIndex
			INTEGER,
		dot5TimerReturnRepeat
			INTEGER,
		dot5TimerHolding
			INTEGER,
		dot5TimerQueuePDU
			INTEGER,
		dot5TimerValidTransmit
			INTEGER,
		dot5TimerNoToken
			INTEGER,
		dot5TimerActiveMon
			INTEGER,
		dot5TimerStandbyMon
			INTEGER,
		dot5TimerErrorReport
			INTEGER,
		dot5TimerBeaconTransmit
			 INTEGER,
		dot5TimerBeaconReceive
			INTEGER
	}

dot5TimerIfIndex  OBJECT-TYPE
	SYNTAX  INTEGER
	ACCESS  read-only
	STATUS  obsolete
	DESCRIPTION
		"The value of this object identifies the
		 802.5 interface for which this entry contains
		 timer values.  The value of this object for a
		 particular interface has the same value as the
		 ifIndex object, defined in [4,6], for the same
		 interface."
	::= { dot5TimerEntry 1 }

dot5TimerReturnRepeat  OBJECT-TYPE
	SYNTAX  INTEGER
	ACCESS  read-only
	STATUS  obsolete
	DESCRIPTION
		"The time-out value used to ensure the
		interface will return to Repeat State, in
		units of 100 micro-seconds.  The value should
		be greater than the maximum ring latency.
		 Implementors are encouraged to provide
		read-write access to this object if that is
		possible/useful in their system, but giving
		due consideration to the dangers of write-able
		timers."
	::= { dot5TimerEntry 2 }

dot5TimerHolding  OBJECT-TYPE
	SYNTAX  INTEGER
	ACCESS  read-only
	STATUS  obsolete
	DESCRIPTION
		"Maximum period of time a station is
		permitted to transmit frames after capturing
		a token, in units of 100 micro-seconds.
		 Implementors are encouraged to provide
		read-write access to this object if that is
		possible/useful in their system, but giving
		due consideration to the dangers of write-able
		timers."
	::= { dot5TimerEntry 3 }

dot5TimerQueuePDU  OBJECT-TYPE
	SYNTAX  INTEGER
	ACCESS  read-only
	STATUS  obsolete
	DESCRIPTION
		"The time-out value for enqueuing of an SMP
		PDU after reception of an AMP or SMP frame in
		which the A and C bits were equal to 0, in
		units of 100 micro-seconds.
		 Implementors are encouraged to provide
		read-write access to this object if that is
		possible/useful in their system, but giving
		due consideration to the dangers of write-able
		timers."
	::= { dot5TimerEntry 4 }

dot5TimerValidTransmit OBJECT-TYPE
	SYNTAX  INTEGER
	ACCESS  read-only
	STATUS  obsolete
	DESCRIPTION
		"The time-out value used by the active monitor
		to detect the absence of valid transmissions,
		in units of 100 micro-seconds.
		 Implementors are encouraged to provide
		read-write access to this object if that is
		possible/useful in their system, but giving
		due consideration to the dangers of write-able
		timers."
	::= { dot5TimerEntry 5 }

dot5TimerNoToken  OBJECT-TYPE
	SYNTAX  INTEGER
	ACCESS  read-only
	STATUS  obsolete
	DESCRIPTION
		"The time-out value used to recover from
		various-related error situations [9]. If N is
		the maximum number of stations on the ring,
		the value of this timer is normally:
		  dot5TimerReturnRepeat + N*dot5TimerHolding.
		 Implementors are encouraged to provide
		read-write access to this object if that is
		possible/useful in their system, but giving
		due consideration to the dangers of write-able
		timers."
	::= { dot5TimerEntry 6 }

dot5TimerActiveMon  OBJECT-TYPE
	SYNTAX  INTEGER
	ACCESS  read-only
	STATUS  obsolete
	DESCRIPTION
		"The time-out value used by the active monitor
		to stimulate the enqueuing of an AMP PDU for
		transmission, in units of 100 micro-seconds.
		 Implementors are encouraged to provide
		read-write access to this object if that is
		possible/useful in their system, but giving
		due consideration to the dangers of write-able
		timers."
	::= { dot5TimerEntry 7 }

dot5TimerStandbyMon  OBJECT-TYPE
	SYNTAX  INTEGER
	ACCESS  read-only
	STATUS  obsolete
	DESCRIPTION
		"The time-out value used by the stand-by
		monitors to ensure that there is an active
		monitor on the ring and to detect a continuous
		stream of tokens, in units of 100 micro-seconds.
		 Implementors are encouraged to provide
		read-write access to this object if that is
		possible/useful in their system, but giving
		due consideration to the dangers of write-able
		timers."
	::= { dot5TimerEntry 8 }

dot5TimerErrorReport  OBJECT-TYPE
	SYNTAX  INTEGER
	ACCESS  read-only
	STATUS  obsolete
	DESCRIPTION
		"The time-out value which determines how often a
		station shall send a Report Error MAC frame to
		report its error counters, in units of 100
		micro-seconds.
		 Implementors are encouraged to provide
		read-write access to this object if that is
		possible/useful in their system, but giving
		due consideration to the dangers of write-able
		timers."
	::= { dot5TimerEntry 9 }

dot5TimerBeaconTransmit  OBJECT-TYPE
	SYNTAX  INTEGER
	ACCESS  read-only
	STATUS  obsolete
	DESCRIPTION
		"The time-out value which determines how long a
		station shall remain in the state of transmitting
		Beacon frames before entering the Bypass state,
		in units of 100 micro-seconds.
		 Implementors are encouraged to provide
		read-write access to this object if that is
		possible/useful in their system, but giving
		due consideration to the dangers of write-able
		timers."
	::= { dot5TimerEntry 10 }

dot5TimerBeaconReceive  OBJECT-TYPE
	SYNTAX  INTEGER
	ACCESS  read-only
	STATUS  obsolete
	DESCRIPTION
		"The time-out value which determines how long a
		station shall receive Beacon frames from its
		downstream neighbor before entering the Bypass
		state, in units of 100 micro-seconds.
		 Implementors are encouraged to provide
		read-write access to this object if that is
		possible/useful in their system, but giving
		due consideration to the dangers of write-able
		timers."
	::= { dot5TimerEntry 11 }

-- 802.5 Interface Tests

dot5Tests OBJECT IDENTIFIER ::= { dot5 3 }

-- The extensions to the interfaces table proposed in [11]
-- define a table object, ifExtnsTestTable, through which a
-- network manager can instruct an agent to test an interface
-- for various faults.  A test to be performed is identified
-- (as the value of ifExtnsTestType) via an OBJECT IDENTIFIER.
--
-- The Full-Duplex Loop Back Test is a common test, defined
-- in [11] as:
--
--    testFullDuplexLoopBack
--
-- Invoking this test on a 802.5 interface causes the interface
-- to check the path from memory through the chip set's internal
-- logic and back to memory, thus checking the proper functioning
-- of the systems's interface to the chip set.


-- The Insert Function test is defined by:

testInsertFunc    OBJECT IDENTIFIER ::= { dot5Tests 1 }

-- Invoking this test causes the station to test the insert ring
-- logic of the hardware if the station's lobe media cable is
-- connected to a wiring concentrator.  Note that this command
-- inserts the station into the network, and thus, could cause
-- problems if the station is connected to a operational network.

-- 802.5 Hardware Chip Sets

dot5ChipSets   OBJECT IDENTIFIER ::= { dot5 4 }

-- The extensions to the interfaces table proposed in [11] define
-- an object, ifExtnsChipSet, with the syntax of OBJECT IDENTIFIER,
-- to identify the hardware chip set in use by an interface.  That
-- definition specifies just one applicable object identifier:
--
--    unknownChipSet
--
-- for use as the value of ifExtnsChipSet when the specific chip
-- set is unknown.
--
-- This MIB defines the following for use as values of ifExtnsChipSet:

-- IBM 16/4 Mb/s
chipSetIBM16  OBJECT IDENTIFIER ::= { dot5ChipSets 1 }

-- TI 4Mb/s
chipSetTItms380    OBJECT IDENTIFIER ::= { dot5ChipSets 2 }

-- TI 16/4 Mb/s
chipSetTItms380c16 OBJECT IDENTIFIER ::= { dot5ChipSets 3 }



-- #include "dot1dBridgeExp.c"


-- The tty Group:
--
-- The following group is used to manage agent terminal ports.
--
--


ttyNumber OBJECT-TYPE
	SYNTAX INTEGER
	ACCESS read-only
	STATUS mandatory
	DESCRIPTION
		"The number of terminal ports on this agent product."
	::= { tty 1 }

ttyTable OBJECT-TYPE
	SYNTAX  SEQUENCE OF TtyEntry
	ACCESS  not-accessible
	STATUS  mandatory
	DESCRIPTION
		"A table of TTY specific information associated with
		this agent."
	::= { tty 2 }

ttyEntry OBJECT-TYPE
	SYNTAX  TtyEntry
	ACCESS  not-accessible
	STATUS  mandatory
	DESCRIPTION
		"A profile of a specific TTY interface associated with
		this agent."
	INDEX	{ ttyIndex }
	::= { ttyTable 1 }

TtyEntry ::=
	SEQUENCE {
		ttyIndex
			INTEGER,
		ttyBaud
			INTEGER,
		ttyParity
			INTEGER,
		ttyStop
			INTEGER,
		ttyData
			INTEGER,
		ttyTimeout
			INTEGER,
		ttyPrompt
			DisplayString,
		ttyDTR
			INTEGER,
		ttyTerminalType

			DisplayString

		}

ttyIndex	OBJECT-TYPE
	SYNTAX  INTEGER
	ACCESS  read-only
	STATUS  mandatory
	DESCRIPTION
		"The TTY to which this entry refers."
	::= { ttyEntry 1 }

ttyBaud		OBJECT-TYPE
	SYNTAX  INTEGER {
		one-hundred-ten(110),
		three-hundred(300),
		twelve-hundred(1200),
		twenty-four-hundred(2400),
		forty-eight-hundred(4800),
		ninety-six-hundred(9600),
		nineteen-two-hundred(19200),
		thirty-eight-thousand-four-hundred(38400)
		}
	ACCESS  read-write
	STATUS  mandatory
	DESCRIPTION
		"The baud rate for this TTY. It should be noted that all
		 serial ports do not support all of the above baud rates."
	::= { ttyEntry 2 }

ttyParity	OBJECT-TYPE
	SYNTAX  INTEGER {
		odd(1),
		even(2),
		none(3)
		}
	ACCESS  read-write
	STATUS  mandatory
	DESCRIPTION
		"The parity setting for this TTY."
	::= { ttyEntry 3 }

ttyStop		OBJECT-TYPE
	SYNTAX  INTEGER {
		one(1),
		two(2)
		}
	ACCESS  read-write
	STATUS  mandatory
	DESCRIPTION
		"The number of stop bits for this TTY."
	::= { ttyEntry 4 }

ttyData		OBJECT-TYPE
	SYNTAX  INTEGER {
		seven(7),
		eight(8)
		}
	ACCESS  read-write
	STATUS  mandatory
	DESCRIPTION
		"The number of data bits for this TTY."
	::= { ttyEntry 5 }

ttyTimeout	OBJECT-TYPE
	SYNTAX  INTEGER
	ACCESS  read-write
	STATUS  mandatory
	DESCRIPTION
		"The number of minutes to wait before this agent logs out
		an inactive login session on this TTY.
		NOTE: In some implementations, this is a single variable
		      that is used by all of the terminal and telnet
		      sessions."
	::= { ttyEntry 6 }

ttyPrompt	OBJECT-TYPE
	SYNTAX  DisplayString (SIZE(0..15))
	ACCESS  read-write
	STATUS  mandatory
	DESCRIPTION
		"The terminal prompt to display on this TTY.
		NOTE: In some implementations, this is a single variable
		      that is used by all of the terminal and telnet
		      sessions."
	::= { ttyEntry 7 }

ttyDTR  OBJECT-TYPE
	SYNTAX  INTEGER {
			asserted(1),
			deasserted(2),
			notApplicable(3)
		}
	ACCESS  read-write
	STATUS  mandatory
	DESCRIPTION
		"This value dictates the behavior of the RS-232 Data
		Terminal Ready (DTR) signal at the time a session ends
		due to a logout, timeout, or shutdown.  This is used by
		some modems as an indication that they should hangup.
		This variable returns notApplicable(3) if the RS-232
		port does not have a DTR signal."
	::= { ttyEntry 8 }

ttyTerminalType   OBJECT-TYPE
      SYNTAX  DisplayString (SIZE(1..40))
      ACCESS  read-write
      STATUS  mandatory
      DESCRIPTION
	      "A string which indicates the type of terminal that
	      is attached to the serial port. It should be noted that
	      the string is passed to a telnet server whenever the server
	      issues the IAC DO TERMINAL-TYPE command (see rfc884)."
      ::= { ttyEntry 9 }


-- The tftp Group
--
-- Implementation of the tftp group is mandatory for all agent
-- products that support TFTP file transfers.
--
-- The tftp Group is used by a station to initiate a TFTP transfer
-- from a TFTP server to this agent (the TFTP client).
--
-- In order to initiate a TFTP file transfer, the client must know
-- the following information:
--
-- 1. The operation to perform, either a get or a put (tftpStart).
-- 2. What station is acting as the TFTP server (tftpIpAddress).
-- 3. The file name (tftpFileName) and the file type (tftpFileType).
--	  The file name can be a pathname.  The file type indicates to
--	  the agent what kind of information is being transferred.
-- 4. What module should receive the file (tftpSlot).
--
--
-- For example, if one wished to inband download flash code to this agent,
-- one would set:
--
-- File type	= Flash code
-- Slot number  = This agent (255).
-- File name	= Pathname on the server where the file is located.
-- IP Address	= The IP of the TFTP file server.
-- TFTP Start	= get - retrieve the file from the server.
--
-- After setting the start object, the transfer takes place.  The
-- tftpResult object contains the result of the last TFTP transfer
-- attempted.
--

tftpStart OBJECT-TYPE
	SYNTAX INTEGER {
		tftpNoTransfer(1),
		tftpGet(2),	-- download to agent
		tftpPut(3)	-- upload to server
		}
	ACCESS read-write
	STATUS mandatory
	DESCRIPTION
		"Setting tftpStart to tftpGet(2) initiates a file
		transfer to the agent (download); tftpPut(3) initiates
		a file transfer to the server (upload)."
	::= { tftp 1 }

tftpSlot OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),

		all-fddi-port-slots(254),

		agent-slot(255)
	}
	ACCESS  read-write
	STATUS  mandatory
	DESCRIPTION
		"The slot number of the module that is to be involved
		in the TFTP transfer with the TFTP server (tftpIpAddress)."
	::= { tftp 2 }

tftpIpAddress OBJECT-TYPE
	SYNTAX IpAddress
	ACCESS read-write
	STATUS mandatory
	DESCRIPTION
		"The IP Address of the TFTP server."
	::= { tftp 3 }

tftpFileName OBJECT-TYPE
	SYNTAX DisplayString (SIZE(0..128))
	ACCESS read-write
	STATUS mandatory
	DESCRIPTION
		"The file name of the file to retrieve (tftpGet), or the
		name of the file to create (tftpPut). "
	::= { tftp 4 }

tftpFileType OBJECT-TYPE
	SYNTAX INTEGER {
		flashCode(1),
		bootCode(2),
		ascii(3)
		}
	ACCESS read-write
	STATUS mandatory
	DESCRIPTION
		"The type of file image to upload/download.  The file
		type indicates to the agent what kind of file it is
		receiving.  flashCode(1) indicates a code upgrade of
		the operational proms.  bootCode(2) indicates a code
		upgrade of the boot proms.  ascii(3) indicates an
		ASCII file."
	::= { tftp 5 }

tftpResult OBJECT-TYPE
	SYNTAX INTEGER {
		clear(1),		-- not initialized
		xferInProgress(2),	-- transfer in progress
		okay(3),		-- no errors
		otherTFTPError(4),	-- undefined error
		fileNotFound(5),	-- check for valid file name
		accessError(6),		-- TFTP access error
		diskFull(7),		-- server disk is full
		illegalTFTPOperation(8),-- illegal TFTP operation
		invalidTFTPTransactionID(9),
		noResponse(10),		-- check valid server IP address
		invalidDownloadKey(11), -- key didn't verify
		invalidSlot(12),
		invalidNetwork(13),
		fepromErase(14),	-- problem erasing
		fepromProg(15),		-- problem programming
		xferError(16),		-- error in transfer
		decodeError(17),
		dlInProgress(18),
		notYetSupported(19),	-- action not yet supported
		noModsOfType(20),	-- no modules of this type in hub
		downloadFailed(21),	-- failure
		crcError(22),		-- file CRC failed
		invalidDLType(23),	-- file not correct
		unknownFEPROMType(24),  -- feprom type unknown
		fileTooLarge(25),	-- file too large for RAM buffering
		fileGetProblem(26),	-- error getting file
		notMaster(27),		-- not master/lost mastership
		onlyOperational(28),	-- if bad cksum, can only dload oper
		rejectedByTarget(29),	-- target rejected the file
		gatewayUnreachable(30), -- gateway is unreachable
		moduleTypeError(31),	-- file module type wrong
		fileTypeError(32),	-- file type (oper/boot) wrong
		fileForwardProblem(33), -- error forwarding file to target
		notifyTargetError(34),  -- error notifying target to dload
		serverTimeout(35),	-- t/o waiting for pkt from server
		noModuleInSlot(36),	-- no module in this slot/sslot
		targetTimeout(37)	-- t/o waiting for target to respond
		}
	ACCESS read-only
	STATUS mandatory
	DESCRIPTION
		"The result of the last TFTP operation."
	::= { tftp 6 }

tftpSubSlot OBJECT-TYPE
	SYNTAX INTEGER
	ACCESS read-write
	STATUS mandatory
	DESCRIPTION
	       "The subslot identifier for the module to be involved
	       in the TFTP transfer with the TFTP server.  If
	       this transfer involves a module not contained in the
	       IBM 8260 system, the value of this object can only be 1.
	       If the value of tftpSlot is agent-slot(255), this

	       object is ignored."

	::= { tftp 7 }

tftpTargetLocation OBJECT-TYPE
	SYNTAX INTEGER {
		target-Device(1),

		target-SlotSubSlot(2)

		}
	ACCESS read-write
	STATUS mandatory
	DESCRIPTION
		"Specifies the ultimate destination of the file
		being transfered.  This object will determine

		if the target is Device or Module."

	::= { tftp 8 }


-- download Group
--
-- To begin an in_band download through SNMP the following mib objects
-- along with the tftp objects must be completed with the correct
-- information.
--
-- Before download is allowed to begin, the agent will verify the
-- Software Key.  If the Software Key is found to be valid, download
-- will follow.  Otherwise, tftpResult is set to (9)invalidDown-
-- loadKey.


downloadUDKSerial OBJECT-TYPE
	SYNTAX DisplayString (SIZE(0..8))
	ACCESS read-write
	STATUS mandatory
	DESCRIPTION
		"A string representing the serial number of the
		 Upgrade Distribution Kit."
	::= { download 1 }

downloadKey OBJECT-TYPE
	SYNTAX DisplayString (SIZE(0..8))
	ACCESS read-write
	STATUS mandatory
	DESCRIPTION

		""

	::= { download 2 }

downloadDateTime OBJECT-TYPE
	SYNTAX DisplayString (SIZE(0..20))
	ACCESS read-only
	STATUS mandatory
	DESCRIPTION
		"The date of the last successful download in the
		 format hh:mm day DD Mon YY"
	::= { download 3 }


alertTable OBJECT-TYPE
	SYNTAX SEQUENCE OF AlertEntry
	ACCESS not-accessible
	STATUS mandatory
	DESCRIPTION
		"A table of entries associated with the management of
		alerts on this agent."
	::= { alert 1 }

alertEntry OBJECT-TYPE
	SYNTAX AlertEntry
	ACCESS not-accessible
	STATUS mandatory
	DESCRIPTION
		"An entry associated with the management of an alert
		on this agent."
	INDEX { alertIndex }
	::= { alertTable 1 }

AlertEntry ::=
	SEQUENCE {
		alertIndex
			INTEGER,
		alertMode
			INTEGER
		}

alertIndex OBJECT-TYPE
	SYNTAX INTEGER {
		snmp-authentication(1),
		hello(2),
		change(3),
		console-display(4),
		port-up-down(5)
		}
	ACCESS  read-only
	STATUS  mandatory
	DESCRIPTION
		"The specific alert to manage.

		snmp-authentication(1) manages the standard authentication
		failure trap.

		hello(2) manages the hello trap.

		change(3), the change traps.

		console-display(4) controls the display of alerts at
		the console terminal.

		port-up-down(5) controls the generation of port up and
		port down traps."
	::= { alertEntry 1 }

alertMode OBJECT-TYPE
	SYNTAX INTEGER {
		enable(1),
		disable(2),
		filter(3)
		}
	ACCESS  read-write
	STATUS  mandatory
	DESCRIPTION
		"Enabling a specific alert allows that alert to be
		generated, or displayed at the console.

		If alertIndex is set to port-up-down(5) then this object
		either overrides the port filter database by enabling or
		disabling all port alerts, or if this object is set to filter(3),
		then portAlertFilter in the portTable is consulted for
		when generating alerts for each individual port.

		Note that only port-up-down(5) alerts may be filtered. Setting
		this object to filter(3) for entries other than port-up-down(5)
		will return the invalidData object."
	::= { alertEntry 2 }



-- The bootp Group
--
-- Implementation of the bootp group is mandatory for all agent
-- products that support the BootP protocol.
--
-- The bootp Group is used by an agent to initiate a BootP request
-- to a BootP server.


bootpStart OBJECT-TYPE
	SYNTAX INTEGER {
		bootpNoTransfer(1),
		bootpRequest(2)
		}
	ACCESS read-write
	STATUS mandatory
	DESCRIPTION
		"Setting bootpStart to bootpRequest(2) initiates an
		BootP request to obtain configuration information from a
		BootP server."
	::= { bootp 1 }

bootpPowerUpMode OBJECT-TYPE
	SYNTAX INTEGER {
		enable(1),
		disable(2)
		}
	ACCESS read-write
	STATUS mandatory
	DESCRIPTION
		"When set to enable(1) indicates that a BootP request to
		obtain configuration information should be initiated
		following a power-up sequence."
	::= { bootp 2 }

bootpIpAddress OBJECT-TYPE
	SYNTAX IpAddress
	ACCESS read-write
	STATUS mandatory
	DESCRIPTION
		"The IP Address of the BootP server. If no IP address is
		defined, the broadcast address will be used in a BootP request."
	::= { bootp 3 }

bootpResult OBJECT-TYPE
	SYNTAX INTEGER {
		clear(1),--not initialized
		xferInProgress(2),
		okay(3),
		noBootPResponse(4),
		otherBootPError(5)
		}
	ACCESS read-only
	STATUS mandatory
	DESCRIPTION
		"The result of the last BootP operation."
	::= { bootp 4 }




-- Chipcom Traps for use by agents.

-- Traps are defined using the conventions in RFC 1215.

ibm8250Hello TRAP-TYPE
	ENTERPRISE	chipcom
--	VARIABLES	{ sysObjectID }
	DESCRIPTION
		"A ibm8250Hello trap is sent every minute by an agent with
		the hello trap enabled.  The hello trap will discontinue
		being sent when either the agent receives an authenticate
		SNMP request, or after 255 minutes."
	::= 1

ibm8250SlotDown TRAP-TYPE
	ENTERPRISE	chipcom
	VARIABLES	{ modSlotIndex }
	DESCRIPTION
		"This trap indicates that the module in the indicated
		slot is down.  Usually, this trap is sent when the module
		has been removed.

		Sometimes, this trap is sent when management communications
		with this module have been broken.  In this case, it may not
		be possible to distinguish between a removed and a failed
		module.  The module type (modType) and the module
		description (modDescr) are also provided in this case."
	::= 2

ibm8250SlotUp TRAP-TYPE
	ENTERPRISE	chipcom
	VARIABLES	{ modSlotIndex }
	DESCRIPTION
		"This trap indicates that a blade in the indicated slot
		is up.  Usually, this trap is sent when the module is
		inserted into the hub.

		Sometimes, this trap is sent when management communications
		have been restored to a module where they had previously
		been broken.  In this case, it may not be possible to
		distinguish between a module that has just be inserted
		and a module that has just the.  The module type (modType)
		and the module description (modDescr) are also provided
		in this case."
	::= 3

ibm8250Environment TRAP-TYPE
	ENTERPRISE	chipcom
	DESCRIPTION
		"A ibm8250Environment trap indicates a change in the
		concentrator's environment has occurred.  The variables
		supplied indicate what exactly changed."
	::= 4

ibm8250Hardware TRAP-TYPE
	ENTERPRISE	chipcom
	DESCRIPTION
		"A ibm8250Hardware trap indicates that a soft hardware
		failure has been detected.  An example of a soft
		hardware failure is too many writes to non-vatile
		storage.  This is an indication to get the unit serviced."
	::= 5

ibm8250Software TRAP-TYPE
	ENTERPRISE	chipcom
	DESCRIPTION
		"A ibm8250Software trap indicates that a soft software
		failure has been detected.  This is an indication
		to get the unit serviced."
	::= 6

ibm8250Change TRAP-TYPE
	ENTERPRISE	chipcom
	DESCRIPTION
		"A ibm8250Change trap is used to indicate that a configuration
		change has occurred.  The actual variables that changed
		are included in the variables section of the PDU."
	::= 7

ibm8250Fatal TRAP-TYPE
	ENTERPRISE	chipcom
	DESCRIPTION
		"A ibm8250Fatal trap is used to indicate that a fatal
		error has occurred.  This is an indication to get
		the unit serviced."
	::= 8

ibm8250TrunkDown TRAP-TYPE
	ENTERPRISE	chipcom
	VARIABLES	{ trunkSlotIndex,
			  trunkIndex,
			  trunkAdminState,
			  trunkStatus }
	DESCRIPTION
		"A ibm8250TrunkDown trap indicates that trunk's status
		has changed to an error condition.  Multiple ibm8250TrunkDown
		traps may be sent if the trunk's status changes from
		one error to another."
	::= 9

ibm8250TrunkUp TRAP-TYPE
	ENTERPRISE	chipcom
	VARIABLES	{ trunkSlotIndex,
			  trunkIndex,
			  trunkAdminState,
			  trunkStatus }
	DESCRIPTION
		"A ibm8250TrunkUp trap indicates that a trunk's status
		has changed to a non-error (okay or warning) condition."

	::= 10

ibm8250PortDown TRAP-TYPE
	ENTERPRISE	chipcom
	VARIABLES	{ portSlotIndex,
			  portIndex,
			  portAdminState,
			  portStatus }
	DESCRIPTION
		"A ibm8250PortDown trap indicates that a port's status
		has changed to an error condition.  Multiple ibm8250PortDown
		traps may be sent if the port's status changes from
		one error to another."
	::= 11

ibm8250PortUp TRAP-TYPE
	ENTERPRISE	chipcom
	VARIABLES	{ portSlotIndex,
			  portIndex,
			  portAdminState,
			  portStatus }
	DESCRIPTION
		"A ibm8250PortUp trap indicates that a port's status
		has changed to a non-error (okay or warning) condition."
	::= 12

ibm8250Ping TRAP-TYPE
	ENTERPRISE	chipcom
	VARIABLES	{ echoAddr, echoNumber, echoResponseCounts }
	DESCRIPTION
		"A ibm8250Ping trap is sent after the SNMP initiated PING
		command is completed.  After the last echo request packet
		is sent, this trap is sent indicating the ping address,
		the number of requests sent, and the number of responses
		received at the time the trap was generated."
	::= 13

ibm8250AboveThreshd TRAP-TYPE
	ENTERPRISE	chipcom
	DESCRIPTION
		"A ibm8250AboveThreshd trap indicates that a Counter or
		 Gauge variable has exceeded its threshd. The variable
		 which is above its threshd is the only variable in
		 the varBind list. Its value is taken at the time the
		 threshd calculation is performed and therefore may be
		 greater than the actual threshd value. Another above
		 threshd trap will not be sent until a below
		 threshd trap is sent."
	::= 14

ibm8250BelowThreshd TRAP-TYPE
	ENTERPRISE	chipcom
	DESCRIPTION
		"A ibm8250BelowThreshd trap indicates that a Counter or
		 Gauge variable had exceeded its threshd but is now
		 below its threshd. The variable which is below its
		 threshd is the only variable in the varBind list.
		 Its value is taken at the time the threshd calculation
		 is performed and therefore may be less than the
		 actual threshd value. Another below threshd trap
		 will not be sent until an above threshd trap is sent."
	::= 15

ibm8250ModuleDown TRAP-TYPE
	ENTERPRISE	chipcom
	VARIABLES	{ ocModSlotIndex, ocModSubSlotIndex,
			ocModType, ocModDescr }
	DESCRIPTION
		"A ibm8250SlotDown trap indicates that management communications
		with the slot indicated by chipModSlotIndex has been
		broken.  This event usually occurs when a module has been
		physically removed from the concentrator.  However, it
		is possible for this event to occur when the particular
		module fails."
	::= 16

ibm8250ModuleUp TRAP-TYPE
	ENTERPRISE	chipcom
	VARIABLES	{ ocModSlotIndex, ocModSubSlotIndex,
			ocModType, ocModDescr }
	DESCRIPTION
		"A ibm8250SlotUp trap indicates that management communications
		with the slot indicated by chipModSlotIndex has been
		established.  This event usually occurs when a module has
		physically been inserted into the concentrator.  The
		variable chipModType indicates the module type inserted.
		For "
	::= 17

ibm8250Security TRAP-TYPE
	ENTERPRISE	chipcom
	VARIABLES	{ netSecTrapReason }
	DESCRIPTION
		"This trap indicates a change in the security environment.
		The netSecTrapReason specifies the reason for the
		trap.

		If the trap reason is intrusion-attempt(2), then the
		following objects will also be included in the trap:
		portSlotIndex and portPortIndex (to specify on which port
		the intrusion attempt occurred), and portAdminState (to
		indicate whether the port was automatically disabled).  The
		enetStatsPortLastSrcAddr object will be included if the
		MAC address of the intruder is available."
	::= 18


END
