-- MIB File Generated on 4-Oct-1995 at 14:37:27

IDS0-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

ids0 OBJECT IDENTIFIER ::= { nas 16 }

-- The USR IDS0 Configuration Group.

ids0CfgTable OBJECT-TYPE
SYNTAX SEQUENCE OF Ids0CfgEntry
ACCESS not-accessible
STATUS mandatory
DESCRIPTION
"A table of operator definable parameters for each DS0"
::= { ids0 1 }

ids0CfgEntry OBJECT-TYPE
SYNTAX Ids0CfgEntry
ACCESS not-accessible
STATUS mandatory
DESCRIPTION
"There is one DS0 Configure entry for each DS0 timeslot in 
the chassis"
INDEX { ids0CfgDs1Index, ids0CfgDs0Index }
::= { ids0CfgTable 1 }

Ids0CfgEntry ::=
SEQUENCE {
ids0CfgDs1Index
    INTEGER,
ids0CfgDs0Index
    INTEGER,
ids0CfgDs0Id
    DisplayString
}

ids0CfgDs1Index OBJECT-TYPE
SYNTAX INTEGER
ACCESS read-only
STATUS mandatory
DESCRIPTION
"The index value which uniquely identifies the CSU to which 
this entry is applicable.  The value of ds0CfgDs1Index 
matches the value of the index for the corresponding DS1 
entity in the entity table of the chassis MIB."
::= { ids0CfgEntry 1 }

ids0CfgDs0Index OBJECT-TYPE
SYNTAX INTEGER
ACCESS read-only
STATUS mandatory
DESCRIPTION
"The index value which uniquely identifies the timeslot of 
the CSU to which this entry refers."
::= { ids0CfgEntry 2 }

ids0CfgDs0Id OBJECT-TYPE
SYNTAX DisplayString (SIZE(0..40))
ACCESS read-write
STATUS mandatory
DESCRIPTION
"An operator definable string useful for easy identification 
of a DS0 relative to the user application."
::= { ids0CfgEntry 3 }

-- The USR IDS0 Status Group.

ids0StatTable OBJECT-TYPE
SYNTAX SEQUENCE OF Ids0StatEntry
ACCESS not-accessible
STATUS mandatory
DESCRIPTION
"USR's DS0 Status table contains various timeslot status 
information."
::= { ids0 2 }

ids0StatEntry OBJECT-TYPE
SYNTAX Ids0StatEntry
ACCESS not-accessible
STATUS mandatory
DESCRIPTION
"There is one entry in the DS0 Status table for each 
timeslot in the chassis."
INDEX { ids0StatDs1Index, ids0StatDs0Index }
::= { ids0StatTable 1 }

Ids0StatEntry ::=
SEQUENCE {
ids0StatDs1Index
    INTEGER,
ids0StatDs0Index
    INTEGER,
ids0StatDs0
    INTEGER,
ids0StatDevConnTo
    INTEGER,
ids0StatSlotConnTo
    INTEGER,
ids0StatChanConnTo
    INTEGER
}

ids0StatDs1Index OBJECT-TYPE
SYNTAX INTEGER
ACCESS read-only
STATUS mandatory
DESCRIPTION
"The index value which uniquely identifies the CSU to which 
this entry is applicable.  The value of ds0StatDs1Index 
matches the value of the index for the coresponding DS1 
entity in the entity table of the chassis MIB."
::= { ids0StatEntry 1 }

ids0StatDs0Index OBJECT-TYPE
SYNTAX INTEGER
ACCESS read-only
STATUS mandatory
DESCRIPTION
"The index value which uniquely identifies the timeslot of 
the CSU to which this entry refers.  The value of 
ds0StatDs0Index matches the value of the index for the 
corresponding DS0 entity in the entity table of the chassis 
MIB."
::= { ids0StatEntry 2 }

ids0StatDs0 OBJECT-TYPE
SYNTAX INTEGER{
  other(1),
  idle(2),
  dialingIn(3),
  dialingOut(4),
  connectedIn(5),
  connectedOut(6),
  ds0CallDisc(22),
  ds0IsDchan(23),
  ds0OutOfServ(24),
  ds0InMaint(25),
  ds0IsFchan(26)
}
ACCESS read-only
STATUS mandatory
DESCRIPTION
"This object indicates the current status of the specified 
timeslot.  The status values change dynamically with system 
operation."
::= { ids0StatEntry 3 }

ids0StatDevConnTo OBJECT-TYPE
SYNTAX INTEGER{
  none(1),
  isdnGateway(2),
  quadModem(3)
}
ACCESS read-only
STATUS mandatory
DESCRIPTION
"This object indicates the device currently connected."
::= { ids0StatEntry 4 }

ids0StatSlotConnTo OBJECT-TYPE
SYNTAX INTEGER (0..16)
ACCESS read-only
STATUS mandatory
DESCRIPTION
"This object indicates the slot of the device currently 
connected. Range = 0(none)-16. "
::= { ids0StatEntry 5 }

ids0StatChanConnTo OBJECT-TYPE
SYNTAX INTEGER (0..4)
ACCESS read-only
STATUS mandatory
DESCRIPTION
"This object indicates the channel of the device currently 
connected.  Range = 0(none)-4."
::= { ids0StatEntry 6 }

-- The USR IDS0 Command Group.

ids0CmdTable OBJECT-TYPE
SYNTAX SEQUENCE OF Ids0CmdEntry
ACCESS not-accessible
STATUS mandatory
DESCRIPTION
"The DS0 Command table contains an entry for each of the 
manageable timeslots in the chassis.  It provides a means 
through which to take specific actions on one or more 
timeslots in the chassis."
::= { ids0 3 }

ids0CmdEntry OBJECT-TYPE
SYNTAX Ids0CmdEntry
ACCESS not-accessible
STATUS mandatory
DESCRIPTION
"There is one entry in the DS0 Command table per timeslot in 
the chassis."
INDEX { ids0CmdDs1Index, ids0CmdDs0Index }
::= { ids0CmdTable 1 }

Ids0CmdEntry ::=
SEQUENCE {
ids0CmdDs1Index
    INTEGER,
ids0CmdDs0Index
    INTEGER,
ids0CmdMgtStationId
    OCTET STRING,
ids0CmdReqId
    INTEGER,
ids0CmdFunction
    INTEGER,
ids0CmdForce
    INTEGER,
ids0CmdParam
    OCTET STRING,
ids0CmdResult
    INTEGER,
ids0CmdCode
    INTEGER
}

ids0CmdDs1Index OBJECT-TYPE
SYNTAX INTEGER
ACCESS read-only
STATUS mandatory
DESCRIPTION
"The index value which uniquely identifies the CSU to which 
this entry is applicable.  The value of ds0CmdDs1Index 
matches the value of the index for the corresponding DS1 
entity in the entity table of the chassis MIB."
::= { ids0CmdEntry 1 }

ids0CmdDs0Index OBJECT-TYPE
SYNTAX INTEGER
ACCESS read-only
STATUS mandatory
DESCRIPTION
"The index which uniquely identifies the timeslot of the 
specified CSU to which this entry is applicable."
::= { ids0CmdEntry 2 }

ids0CmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with ds0CmdReqId and ds0CmdResult 
to detect interference from other MSs."
::= { ids0CmdEntry 3 }

ids0CmdReqId OBJECT-TYPE
SYNTAX INTEGER
ACCESS read-only
STATUS mandatory
DESCRIPTION
"This object contains the value of the request-id field in 
the SNMP PDU which invoked the current or most recent 
command on this DS0 entity.  If the request-id is unknown 
or undefined, this object contains the zero value."
::= { ids0CmdEntry 4 }

ids0CmdFunction OBJECT-TYPE
SYNTAX INTEGER{
  noCommand(1),
  disconnect(2)
}
ACCESS read-write
STATUS mandatory
DESCRIPTION
"This object contains a value that identifies the command 
being requested."
::= { ids0CmdEntry 5 }

ids0CmdForce OBJECT-TYPE
SYNTAX INTEGER{
  force(1),
  noForce(2)
}
ACCESS read-write
STATUS mandatory
DESCRIPTION
"In some cases, the DS0 entity may be in a state such that 
certain commands could adversely affect connections.  In 
such cases, a command request with ds0CmdForce not defined, 
or set to noForce will result in a warning.  If the 
operator elects to ignore such warnings, ds0CmdForce can be 
set to force in a re-issued request and the command will be 
carried out regardless of its potentially hazzardous 
effects."
::= { ids0CmdEntry 6 }

ids0CmdParam OBJECT-TYPE
SYNTAX OCTET STRING (SIZE(0..24))
ACCESS read-write
STATUS mandatory
DESCRIPTION
"This object contains parameters that are specific to the 
particular command being issued.  In some cases, there will 
be no additional parameters required."
::= { ids0CmdEntry 7 }

ids0CmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command, or the value none(1) if no commands have 
been requested since the last reset."
::= { ids0CmdEntry 8 }

ids0CmdCode OBJECT-TYPE
SYNTAX INTEGER{
  noError(1),
  unable(2),
  unrecognizedCommand(6),
  slotEmpty(8),
  noResponse(12),
  unsupportedCommand(20),
  deviceDisabled(22),
  pendingSoftwareDownload(73)
}
ACCESS read-only
STATUS mandatory
DESCRIPTION
"The value of this object upon command completion indicates 
a further description of what went wrong if the command was 
unsuccessful."
::= { ids0CmdEntry 9 }

END
