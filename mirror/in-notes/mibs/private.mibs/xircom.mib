XIRCOM-MIB

	DEFINITIONS ::= BEGIN


	IMPORTS 
		enterprises
			FROM RFC1155-SMI
		OBJECT-TYPE
			FROM RFC-1212
		TRAP-TYPE
			FROM RFC-1215;

	-- Xircom private enterprises MIB extensions
	xircom         OBJECT IDENTIFIER ::= { enterprises 588 }

	-- examples MIB
	printers        OBJECT IDENTIFIER ::= { xircom 1 }

	-- define a couple of objects
	printerStatus   OBJECT-TYPE
		SYNTAX  INTEGER
		ACCESS  read-only
		STATUS  mandatory
		DESCRIPTION     "Bitfield with the following bit
				 positions defined
					bit 0 - other error
					bit 1 - paper out
					bit 2 - io error
					bit 3 - offline"

		::= { printers 1 }

	acceptPrintJobs   OBJECT-TYPE
		SYNTAX  INTEGER
		ACCESS  read-write
		STATUS  mandatory
		DESCRIPTION     "Set to one if the system is accepting
				 new print jobs "
		::= { printers 2 }


	queuedJobs   OBJECT-TYPE
		SYNTAX  INTEGER
		ACCESS  read-only
		STATUS  mandatory
		DESCRIPTION     "the number of queued print jobs "
		::= { printers 3 }

	sendTrap   OBJECT-TYPE
		SYNTAX  INTEGER
		ACCESS  read-write
		STATUS  mandatory
		DESCRIPTION     "Bitfield with the following bit
				 positions defined
					bit 0 - other error
					bit 1 - paper out
					bit 2 - io error
					bit 3 - offline

				 If the bit is set, a trap is sent when the
				 status of that bit position in printerStatus
				 changes"

		::= { printers 4 }

	printerTrap  TRAP-TYPE
		ENTERPRISE      printers
		VARIABLES       { printerStatus }
		DESCRIPTION     "The printer status changed"
		::= 0

	END
