-- MIB File Generated on 18-Oct-1995 at 08:16:59

DT1-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

dt1 OBJECT IDENTIFIER ::= { nas 3 }

-- The Dual T1 Card Identification Group.

dt1Id OBJECT IDENTIFIER ::= { dt1 1 }

dt1IdTable OBJECT-TYPE
SYNTAX SEQUENCE OF Dt1IdEntry
ACCESS not-accessible
STATUS mandatory
DESCRIPTION
"A table that contains information that identifies the 
hardware and software that make up the specified dual T1 
card."
::= { dt1Id 1 }

dt1IdEntry OBJECT-TYPE
SYNTAX Dt1IdEntry
ACCESS not-accessible
STATUS mandatory
DESCRIPTION
"There is one entry in this table for every dual T1 card in 
the chassis."
INDEX { dt1IdIndex }
::= { dt1IdTable 1 }

Dt1IdEntry ::=
SEQUENCE {
dt1IdIndex
    INTEGER,
dt1IdHardwareSerNum
    DisplayString,
dt1IdHardwareRev
    DisplayString,
dt1IdSoftwareRev
    DisplayString
}

dt1IdIndex OBJECT-TYPE
SYNTAX INTEGER
ACCESS read-only
STATUS mandatory
DESCRIPTION
"An index that uniquely identifies the dual T1 card for 
which this row in the table pertains.  The value of this 
index matches the value of the index for the corresponding 
entity in the entity table of the chassis MIB."
::= { dt1IdEntry 1 }

dt1IdHardwareSerNum OBJECT-TYPE
SYNTAX DisplayString (SIZE(0..24))
ACCESS read-only
STATUS mandatory
DESCRIPTION
"The dual T1 card's hardware serial number as stored in 
EEPROM."
::= { dt1IdEntry 2 }

dt1IdHardwareRev OBJECT-TYPE
SYNTAX DisplayString (SIZE(0..24))
ACCESS read-only
STATUS mandatory
DESCRIPTION
"The hardware revision of the specified dual T1 card as 
stored in its EEPROM."
::= { dt1IdEntry 3 }

dt1IdSoftwareRev OBJECT-TYPE
SYNTAX DisplayString (SIZE(0..24))
ACCESS read-only
STATUS mandatory
DESCRIPTION
"The revision of the software being executed in the 
specified dual T1 card."
::= { dt1IdEntry 4 }

-- The Dual T1 Card Configuration Group.

dt1Cfg OBJECT IDENTIFIER ::= { dt1 2 }

dt1CfgTable OBJECT-TYPE
SYNTAX SEQUENCE OF Dt1CfgEntry
ACCESS not-accessible
STATUS mandatory
DESCRIPTION
"The Dual T1 Card Configuration Table contains an entry for 
each of the manageable Dual T1 Cards in the chassis.  It 
contains objects that reflect the current configuration of 
parameters that affect the operation of all the entities 
that reside on the given card."
::= { dt1Cfg 1 }

dt1CfgEntry OBJECT-TYPE
SYNTAX Dt1CfgEntry
ACCESS not-accessible
STATUS mandatory
DESCRIPTION
"There is one Dual T1 Card Configuration table entry per 
Dual T1 Card in the chassis."
INDEX { dt1CfgIndex }
::= { dt1CfgTable 1 }

Dt1CfgEntry ::=
SEQUENCE {
dt1CfgIndex
    INTEGER,
dt1CfgSpanATmgSrcPrio
    INTEGER,
dt1CfgSpanBTmgSrcPrio
    INTEGER,
dt1CfgInternTmgSrcPrio
    INTEGER,
dt1CfgTdmBusTmgSrcPrio
    INTEGER
}

dt1CfgIndex OBJECT-TYPE
SYNTAX INTEGER
ACCESS read-only
STATUS mandatory
DESCRIPTION
"A unique value for each Dual T1 Card in the chassis.  The 
value of dt1CfgIndex matches the value of the index for the 
corresponding Dual T1 Card entity in the entity table of 
the chassis MIB."
::= { dt1CfgEntry 1 }

dt1CfgSpanATmgSrcPrio OBJECT-TYPE
SYNTAX INTEGER{
  notAllowed(1),
  high(2),
  mediumHigh(3),
  medium(4),
  low(5)
}
ACCESS read-write
STATUS mandatory
DESCRIPTION
"Identifies the priority at which the clock recovered from 
span line A is to be used as this Dual T1 Card's transmit 
timing source."
::= { dt1CfgEntry 2 }

dt1CfgSpanBTmgSrcPrio OBJECT-TYPE
SYNTAX INTEGER{
  notAllowed(1),
  high(2),
  mediumHigh(3),
  medium(4),
  low(5)
}
ACCESS read-write
STATUS mandatory
DESCRIPTION
"Identifies the priority at which the clock recovered from 
span line B is to be used as this Dual T1 Card's transmit 
timing source."
::= { dt1CfgEntry 3 }

dt1CfgInternTmgSrcPrio OBJECT-TYPE
SYNTAX INTEGER{
  notAllowed(1),
  high(2),
  mediumHigh(3),
  medium(4),
  low(5)
}
ACCESS read-write
STATUS mandatory
DESCRIPTION
"Identifies the priority at which this Dual T1 Card's 
internal clock is to be used as the transmit timing source."
::= { dt1CfgEntry 4 }

dt1CfgTdmBusTmgSrcPrio OBJECT-TYPE
SYNTAX INTEGER{
  notAllowed(1),
  high(2),
  mediumHigh(3),
  medium(4),
  low(5)
}
ACCESS read-write
STATUS mandatory
DESCRIPTION
"Identifies the priority at which the clock currently on the 
TDM bus is to be used as this Dual T1 Card's transmit 
timing source."
::= { dt1CfgEntry 5 }

-- The Dual T1 Card Status Group.

dt1Stat OBJECT IDENTIFIER ::= { dt1 3 }

dt1StatTable OBJECT-TYPE
SYNTAX SEQUENCE OF Dt1StatEntry
ACCESS not-accessible
STATUS mandatory
DESCRIPTION
"The Dual T1 Card Status table contains an entry for each of 
the manageable Dual T1 Cards in the chassis.  It contains 
objects that reflect the current card specific status.  
Status values dynamically change during calls, and they are 
read-only."
::= { dt1Stat 1 }

dt1StatEntry OBJECT-TYPE
SYNTAX Dt1StatEntry
ACCESS not-accessible
STATUS mandatory
DESCRIPTION
"There is one Dual T1 Card Status entry per Dual T1 Card in 
the chassis."
INDEX { dt1StatIndex }
::= { dt1StatTable 1 }

Dt1StatEntry ::=
SEQUENCE {
dt1StatIndex
    INTEGER,
dt1StatCurrentTmgSrc
    INTEGER,
dt1StatSelfTest
    INTEGER
}

dt1StatIndex OBJECT-TYPE
SYNTAX INTEGER
ACCESS read-only
STATUS mandatory
DESCRIPTION
"A unique value for each Dual T1 Card in the chassis.  The 
value of dt1StatusIndex matches the value of the index for 
the corresponding Dual T1 Card's entry in the entity table 
of the chassis MIB."
::= { dt1StatEntry 1 }

dt1StatCurrentTmgSrc OBJECT-TYPE
SYNTAX INTEGER{
  spanLineA(1),
  spanLineB(2),
  internalClock(3),
  tdmBusClock(4)
}
ACCESS read-only
STATUS mandatory
DESCRIPTION
"Based on the availability of the various timing sources and 
the current settings of the priorities at which they are to 
be used, the Dual T1 Card will select the current transmit 
timing source.  This object will indicate the current 
timing source being used for transmit timing."
::= { dt1StatEntry 2 }

dt1StatSelfTest OBJECT-TYPE
SYNTAX INTEGER
ACCESS read-only
STATUS mandatory
DESCRIPTION
"This object contains the result of the last self test 
command requested from the command table.  It includes both 
destructive and non destructive results."
::= { dt1StatEntry 3 }

-- The Dual T1 Card Command Group.

dt1Cmd OBJECT IDENTIFIER ::= { dt1 4 }

dt1CmdTable OBJECT-TYPE
SYNTAX SEQUENCE OF Dt1CmdEntry
ACCESS not-accessible
STATUS mandatory
DESCRIPTION
"The Dual T1 Card Command table contains an entry for each 
of the manageable Dual T1 Cards in the chassis.  It 
provides a means through which to take specific actions on 
one or more Dual T1 cards in the NAS chassis.  The number 
of entries in this table is given by the value of 
dt1IdNumber."
::= { dt1Cmd 1 }

dt1CmdEntry OBJECT-TYPE
SYNTAX Dt1CmdEntry
ACCESS not-accessible
STATUS mandatory
DESCRIPTION
"There is one Dual T1 Card Command entry per Dual T1 Card in 
the chassis."
INDEX { dt1CmdIndex }
::= { dt1CmdTable 1 }

Dt1CmdEntry ::=
SEQUENCE {
dt1CmdIndex
    INTEGER,
dt1CmdMgtStationId
    OCTET STRING,
dt1CmdReqId
    INTEGER,
dt1CmdFunction
    INTEGER,
dt1CmdForce
    INTEGER,
dt1CmdParam
    OCTET STRING,
dt1CmdResult
    INTEGER,
dt1CmdCode
    INTEGER
}

dt1CmdIndex OBJECT-TYPE
SYNTAX INTEGER
ACCESS read-only
STATUS mandatory
DESCRIPTION
"A unique value for each Dual T1 Card in the chassis.  The 
value of this object matches the value of the index of the 
corresponding Dual T1 Card's entry in the entity table of 
the chassis MIB."
::= { dt1CmdEntry 1 }

dt1CmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with dt1CmdReqId and dt1CmdResult 
to detect interference from other MSs."
::= { dt1CmdEntry 2 }

dt1CmdReqId OBJECT-TYPE
SYNTAX INTEGER
ACCESS read-only
STATUS mandatory
DESCRIPTION
"This object contains the value of the request-id field in 
the SNMP PDU which invoked the current or most recent 
command or test on this Dual T1 Card.  If the request-id is 
unknown or undefined, this object contains the value zero."
::= { dt1CmdEntry 3 }

dt1CmdFunction OBJECT-TYPE
SYNTAX INTEGER{
  noCommand(1),
  saveToNVRAM(2),
  restoreFromNVRAM(3),
  restoreFromDefault(4),
  nonDisruptSelfTest(5),
  disruptSelfTest(6),
  softwareReset(7),
  resetToHiPrioTimingSrc(8),
  forceTdmBusMastership(9)
}
ACCESS read-write
STATUS mandatory
DESCRIPTION
"This object contains a value which describes the command 
which is being invoked."
::= { dt1CmdEntry 4 }

dt1CmdForce OBJECT-TYPE
SYNTAX INTEGER{
  force(1),
  noForce(2)
}
ACCESS read-write
STATUS mandatory
DESCRIPTION
"In some cases, the Dual T1 Card may be in a state such that 
certain commands could adversely affect connections.  In 
such cases, a command request with this object not present 
or set to noForce will result in a warning.  If the 
operator elects to ignore such warnings, this object can be 
set to force in a subsequent issue of the command to cause 
the command to be carried out regardless of its potentially 
hazzardous effects."
::= { dt1CmdEntry 5 }

dt1CmdParam OBJECT-TYPE
SYNTAX OCTET STRING (SIZE(0..24))
ACCESS read-write
STATUS mandatory
DESCRIPTION
"This object contains parameters that are specific to the 
particular command being issued.  In some cases, there will 
be no aditional parameters required."
::= { dt1CmdEntry 6 }

dt1CmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { dt1CmdEntry 7 }

dt1CmdCode OBJECT-TYPE
SYNTAX INTEGER{
  noError(1),
  unable(2),
  unrecognizedCommand(6),
  slotEmpty(8),
  noResponse(12),
  unsupportedCommand(20),
  deviceDisabled(22),
  testFailed(25),
  userInterfaceActive(58),
  pendingSoftwareDownload(73)
}
ACCESS read-only
STATUS mandatory
DESCRIPTION
"The value of this object upon command completion indicates 
a further description of what went wrong if the command was 
unsuccessful.  In the case of tests, a bit mapped result of 
each of the sub-tests performed can be found in the status 
table."
::= { dt1CmdEntry 8 }

dt1TrapEnaTable OBJECT-TYPE
SYNTAX SEQUENCE OF Dt1TrapEnaEntry
ACCESS not-accessible
STATUS mandatory
DESCRIPTION
"Table containing objects to enable traps on the Dual T1 
Cards in the chassis."
::= { dt1 5 }

dt1TrapEnaEntry OBJECT-TYPE
SYNTAX Dt1TrapEnaEntry
ACCESS not-accessible
STATUS mandatory
DESCRIPTION
"There is one entry for each Dual T1 Card in the chassis."
INDEX { dt1TrapEnaIndex }
::= { dt1TrapEnaTable 1 }

Dt1TrapEnaEntry ::=
SEQUENCE {
dt1TrapEnaIndex
    INTEGER,
dt1TrapEnaTxTmgSrcSwitch
    INTEGER
}

dt1TrapEnaIndex OBJECT-TYPE
SYNTAX INTEGER
ACCESS read-only
STATUS mandatory
DESCRIPTION
"A unique index identifying the Dual T1 Card to which the 
trap enable objects pertain."
::= { dt1TrapEnaEntry 1 }

dt1TrapEnaTxTmgSrcSwitch OBJECT-TYPE
SYNTAX INTEGER{
  enable(1),
  disable(2)
}
ACCESS read-write
STATUS mandatory
DESCRIPTION
"An object which enables the SNMP proxy agent to generate a 
trap upon detection of the Dual T1 Card switching to an 
alternate transmit timing source."
::= { dt1TrapEnaEntry 2 }

END
