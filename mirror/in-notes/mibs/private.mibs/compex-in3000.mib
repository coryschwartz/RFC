--
--
-- Copyright (C) by Compex, Inc. All rights reserved
-- 
-- IN3000 MIB
--
-- Andrew Fyke 
--
-- 714-630-7302 ex.143
-- (afyke@orion.oac.uci.edu)
--



COMPEX-IN3000 DEFINITIONS ::= BEGIN


compex OBJECT IDENTIFIER ::= { 1 3 6 1 4 1 426 }
in3000 OBJECT IDENTIFIER ::= { compex 1 }

hubTypes OBJECT IDENTIFIER ::= { in3000 1 }
 
tp3000 OBJECT IDENTIFIER ::= { hubTypes 1 }
rp3000 OBJECT IDENTIFIER ::= { hubTypes 2 }

--
-- The product information portion of this MIB stores general
-- device information.
--

productInfo 	OBJECT IDENTIFIER ::= { in3000 2 }

productName	OBJECT-TYPE
	SYNTAX 	DisplayString (SIZE(0..255))
	ACCESS	read-only
	STATUS	mandatory
	DESCRIPTION
		"The textual description of the IN3000."
::= { productInfo 1}
	
productVersion OBJECT-TYPE
	SYNTAX	DisplayString (SIZE(0..32))
	ACCESS 	read-only
	STATUS	mandatory
	DESCRIPTION
		"The version of the IN3000 Firmware."
::= { productInfo 2}

releasedDate OBJECT-TYPE
	SYNTAX	DisplayString (SIZE(0..100))
	ACCESS 	read-only
	STATUS	mandatory
	DESCRIPTION
		"The release date of this version."
::= { productInfo 3}

compexAddress OBJECT-TYPE 
	SYNTAX 	DisplayString (SIZE(0..255))
	ACCESS	read-only
	STATUS	mandatory
	DESCRIPTION
		"Address of Compex, Inc."
::= { productInfo 4}

compexPhone OBJECT-TYPE
	SYNTAX	DisplayString (SIZE(0..100))
	ACCESS 	read-only
	STATUS	mandatory
	DESCRIPTION
		"Compex's phone number for technical support
		 or sales information."
::= { productInfo 5}

compexImage OBJECT-TYPE
	SYNTAX	OCTET STRING 
	ACCESS 	read-only
	STATUS	mandatory
	DESCRIPTION
		"Information on the system setup.

		This string is not in a human readable form."
::= { productInfo 6}

compexMyAccess OBJECT-TYPE
	SYNTAX	INTEGER
	{
		readOnly(1),
		readWrite(2)
	}
	ACCESS 	read-only
	STATUS	mandatory
	DESCRIPTION
		"This tells you the access you have with the
		community string you are using."
::= { productInfo 7}

devTeamTable OBJECT-TYPE
     	SYNTAX  SEQUENCE OF DevTeamEntry
      	ACCESS  not-accessible
      	STATUS  mandatory
      	DESCRIPTION
		"This is a list of the Compex development team."
::= { productInfo 8 }

devTeamEntry OBJECT-TYPE
	SYNTAX  DevTeamEntry
      	ACCESS  not-accessible
     	STATUS  mandatory
      	DESCRIPTION
	      	"Information about a particular person.

		The index is the cpId of the person."
      	INDEX   { cpId }
::= { devTeamTable 1 }

DevTeamEntry ::=
      	SEQUENCE {
	  cpId
	    INTEGER,
	  cpName
	    DisplayString
      	}

cpId OBJECT-TYPE
SYNTAX  INTEGER 
ACCESS  read-only
STATUS  mandatory
DESCRIPTION
	"This is the development team member's unique
	identifier number."
::= { devTeamEntry 1 }

cpName OBJECT-TYPE
SYNTAX  DisplayString (SIZE(1..40))  
ACCESS  read-only
STATUS  mandatory
DESCRIPTION
	"This is the development team member's name."
::= { devTeamEntry 2 }



--
-- The Community Info portion of the MIB is used to store
-- the legal community strings for the agent.
--
communityInfo 	OBJECT IDENTIFIER ::= { in3000 3 }

communityTable OBJECT-TYPE
     	SYNTAX  SEQUENCE OF CommunityEntry
      	ACCESS  not-accessible
      	STATUS  mandatory
      	DESCRIPTION
		"A table containing community string information."
::= { communityInfo 1 }

communityEntry OBJECT-TYPE
	SYNTAX  CommunityEntry
      	ACCESS  not-accessible
     	STATUS  mandatory
      	DESCRIPTION
	      	"Information about a particular community string.

		The instance of the table entries is the
		communityInstance."
      	INDEX   { communityInstance }
::= { communityTable 1 }

CommunityEntry ::=
      	SEQUENCE {
	  communityInstance
	    INTEGER,
	  communityString
	    DisplayString,
	  communityCapability
	    INTEGER 
      	}

communityInstance OBJECT-TYPE
SYNTAX  INTEGER (1..10)
ACCESS  read-only
STATUS  mandatory
DESCRIPTION
	" The table instance. This is the row number of a particular
	community string in the table."
::= { communityEntry 1 }

communityString OBJECT-TYPE
      	SYNTAX  DisplayString (SIZE(1..10))
      	ACCESS  read-write
      	STATUS  mandatory
      	DESCRIPTION
	      	"The community string. This is defined in RFC 1157.
		The community string may be up to 10 characters
		in length."
::= { communityEntry 2 }

communityCapability OBJECT-TYPE
	SYNTAX  INTEGER {
		readOnly(1),
		readWrite(2),
		clear(99)
		}
      	ACCESS  read-write
      	STATUS  mandatory
     	DESCRIPTION
		"The capability of the community string.  The
		community string may be valid for different SNMP
		operations. Setting this object to 'clear' will
		cause the entry to be cleared out."
::= { communityEntry 3 }

--
-- The trap information table stores information associated
-- with the SNMP manager that will receive traps generated by the
-- IN3000.
--
trapInfo 	OBJECT IDENTIFIER ::= { in3000 4 }

trapTable OBJECT-TYPE
     	SYNTAX  SEQUENCE OF TrapEntry
      	ACCESS  not-accessible
      	STATUS  mandatory
      	DESCRIPTION
		"A table containing trap receiver information."
::= { trapInfo 1 }

trapEntry OBJECT-TYPE
	SYNTAX  TrapEntry
      	ACCESS  not-accessible
     	STATUS  mandatory
      	DESCRIPTION
	      	"Information about a particular trap receiver.

		The instance for this table is the trapDest, or
		the IP address of the trap receiver.

		This table may have up to ten entries."
      	INDEX   { trapDest }
::= { trapTable 1 }

TrapEntry ::=
      	SEQUENCE {
	  trapDest
	    IpAddress, 
	  trapStatus
	    INTEGER
      	}

trapDest OBJECT-TYPE
      	SYNTAX  IpAddress
      	ACCESS  read-write
      	STATUS  mandatory
      	DESCRIPTION
	      	"The trap destination. This is defined in RFC 1157.
		The trap received should be the IP address of
		an SNMP based network management system."
::= { trapEntry 1 }

trapStatus OBJECT-TYPE
      	SYNTAX  INTEGER
      		{
		ok(1),
		delete(2) 
      		}
      	ACCESS  read-write
      	STATUS  mandatory
      	DESCRIPTION
	      	"The trap status. This MIB variable is used to delete
		a trap receiver from the trap table."
::= { trapEntry 2 }

--
-- This group contains MIB variables that are global to the
-- IN3000. 
--

in3000StatsRptr    OBJECT IDENTIFIER ::= { in3000 5 }

rptrFifoColls OBJECT-TYPE
	SYNTAX	Counter
	ACCESS 	read-only
	STATUS	mandatory
	DESCRIPTION
		"The total number of Collision Designators put into
		the IN3000's FIFO."
::= { in3000StatsRptr 1 }

rptrShortWoPort OBJECT-TYPE
	SYNTAX	Counter
	ACCESS 	read-only
	STATUS	mandatory
	DESCRIPTION
		"The total number of short fragment put into the
		IN3000's FIFO without a port designator."
::= { in3000StatsRptr 2 }

rptrNoStatsDsgntr OBJECT-TYPE
	SYNTAX	Counter
	ACCESS 	read-only
	STATUS	mandatory
	DESCRIPTION
		"The total number of empty statistic designators
		put into the IN3000's FIFO."
::= { in3000StatsRptr 3 }

rptrInvalidDesgntr OBJECT-TYPE
	SYNTAX	Counter
	ACCESS 	read-only
	STATUS	mandatory
	DESCRIPTION
		"The total number of entries put into the IN3000's
		FIFO that had invalid designators."
::= { in3000StatsRptr 4 }

rptrPortIDwoPacket OBJECT-TYPE
	SYNTAX	Counter
	ACCESS 	read-only
	STATUS	mandatory
	DESCRIPTION
		"The total number of entries in the IN3000's FIFO
		which do not have a corresponding packet in the
		ethernet controller's RAM buffer."
::= { in3000StatsRptr 5 }

rptrOverflows OBJECT-TYPE
	SYNTAX	Counter
	ACCESS 	read-only
	STATUS	mandatory
	DESCRIPTION
		"The total number of times the IN3000's FIFO has
		overflowed."
::= { in3000StatsRptr 6 }

rptrNoFreeBuffers OBJECT-TYPE
	SYNTAX	Counter
	ACCESS 	read-only
	STATUS	mandatory
	DESCRIPTION
		"The number of packets received that had to
		be discarded due to lack of buffers." 
::= { in3000StatsRptr 7 }

rptrTxTimeouts OBJECT-TYPE
	SYNTAX	Counter
	ACCESS 	read-only
	STATUS	mandatory
	DESCRIPTION
		"The total number of times a packet could not be
		sent before the transmit timer expired."
::= { in3000StatsRptr 8 }

rptrNICTxCollisions OBJECT-TYPE
	SYNTAX	Counter
	ACCESS 	read-only
	STATUS	mandatory
	DESCRIPTION
		"The total number of collision that occured
		while the ethernet controller attempted to transmit.
		This error is reported by the ethernet controller."
::= { in3000StatsRptr 9 }

rptrNICTxFifoUruns OBJECT-TYPE
	SYNTAX	Counter
	ACCESS 	read-only
	STATUS	mandatory
	DESCRIPTION
		"The total number of times the ethernet controller
		could not gain access to the ethernet before the
		ethernet controller's FIFO emptied."
::= { in3000StatsRptr 10 }

rptrNICTxCDHrtbts OBJECT-TYPE
	SYNTAX	Counter
	ACCESS 	read-only
	STATUS	mandatory
	DESCRIPTION
		"The number of times the ethernet controlled was
		unable to transmit a collision signal after
		transmission of a packet."
::= { in3000StatsRptr 11 }

rptrNICTxOutWinCls OBJECT-TYPE
	SYNTAX	Counter
	ACCESS 	read-only
	STATUS	mandatory
	DESCRIPTION
		"The total number of collisions seen by the ethernet
		controller that occured after the slot time."
::= { in3000StatsRptr 12 }

rptrNICCarrierLost OBJECT-TYPE
	SYNTAX	Counter
	ACCESS 	read-only
	STATUS	mandatory
	DESCRIPTION
		"The total number of times a carrier lost was
		detected by the ethernet controlled during the
		transmission of a packet."
::= { in3000StatsRptr 13 }

rptrInNoRxBuf OBJECT-TYPE
	SYNTAX	Counter
	ACCESS 	read-only
	STATUS	mandatory
	DESCRIPTION
		"The total number of times a packet was discarded
		due to lack of receive buffers."
::= { in3000StatsRptr 14 }

--
-- Extra IN3000 Group Level Octets Statistics 

in3000StatsGroup       OBJECT IDENTIFIER ::= { in3000 6 }	

groupOctetsTable OBJECT-TYPE
     	SYNTAX  SEQUENCE OF GroupOctetsEntry
      	ACCESS  not-accessible
      	STATUS  mandatory
      	DESCRIPTION
		"This table contains Repeater Group Level octets
		Statistics."
::= { in3000StatsGroup 1 }

groupOctetsEntry OBJECT-TYPE
	SYNTAX  GroupOctetsEntry
      	ACCESS  not-accessible
     	STATUS  mandatory
      	DESCRIPTION
	      	"Each row of this table is associated to a TP3000
		or RP3000. Note the the groups are numbered from
		1 to 4."
      	INDEX   { gsoGroupIndex }
::= { groupOctetsTable 1 }

GroupOctetsEntry ::=
      	SEQUENCE {
	  gsoGroupIndex
	    INTEGER,
          gsoHostOctetsRxOk
            Counter,
          gsoHostOctetsRxErr
            Counter,
          gsoOctetsRxOk
            Counter,
          gsoOctetsRxErr
            Counter,
          gsobkt64Ok 
            Counter,
          gsobkt64Err 
            Counter,
          gsobkt65to127Ok 
            Counter,
          gsobkt65to127Err 
            Counter,
          gsobkt128to255Ok 
            Counter,
          gsobkt128to255Err 
            Counter,
          gsobkt256to511Ok 
            Counter,
          gsobkt256to511Err 
            Counter,
          gsobkt512to1023Ok 
            Counter,
          gsobkt512to1023Err 
            Counter,
          gsobkt1024to1518Ok 
            Counter,
          gsobkt1024to1518Err 
            Counter,
          gsoRuntPacketsOk 
            Counter,
          gsoRuntPacketsErr 
            Counter,
          gsoPacketsTooBigOk 
            Counter,
          gsoPacketsTooBigErr 
            Counter
       	}

gsoGroupIndex OBJECT-TYPE
      	SYNTAX  INTEGER
      	ACCESS  read-only
      	STATUS  mandatory
      	DESCRIPTION
	      	"A unique value to the group. The groups are numbered
		from 1 to 4. The addresses set via the dip switches
		on the TP3000 and RP3000 are numbered 0 to 3. In
		order to calculate the group number add one (1) to
		the address set via the TP3000 or RP3000 dip switches."
::= { groupOctetsEntry 1 }

gsoHostOctetsRxOk OBJECT-TYPE
      	SYNTAX  Counter
      	ACCESS  read-only
      	STATUS  mandatory
      	DESCRIPTION
	      	"The total number of octets received by all ports
		in the group that were from valid packets and were
		addressed to the IN3000."
::= { groupOctetsEntry 2 }

gsoHostOctetsRxErr OBJECT-TYPE
      	SYNTAX  Counter
      	ACCESS  read-only
      	STATUS  mandatory
      	DESCRIPTION
	      	"The total number of octets received by all ports
		in the group that were from packets with errors and
		were addressed to the IN3000."
::= { groupOctetsEntry 3 }

gsoOctetsRxOk OBJECT-TYPE
      	SYNTAX  Counter
      	ACCESS  read-only
      	STATUS  mandatory
      	DESCRIPTION
	      	"The total number of octets received by all ports
		in the group that were from valid packets and were
		no addressed to the IN3000."
::= { groupOctetsEntry 4 }

gsoOctetsRxErr OBJECT-TYPE
      	SYNTAX  Counter
      	ACCESS  read-only
      	STATUS  mandatory
      	DESCRIPTION
	      	"The total number of octets received by all ports
		in the group that were from packets with errors and
		were not addressed to the IN3000."
::= { groupOctetsEntry 5 }

gsobkt64Ok OBJECT-TYPE
      	SYNTAX  Counter
      	ACCESS  read-only
      	STATUS  mandatory
      	DESCRIPTION
	      	"The total number of packets received from all
		ports in the group that were 64 bytes in length
		(including FCS octets and excluding framing bits)
		and did not contain errors."
::= { groupOctetsEntry 6 }

gsobkt64Err OBJECT-TYPE
      	SYNTAX  Counter
      	ACCESS  read-only
      	STATUS  mandatory
      	DESCRIPTION
	      	"The total number of packets received from all
		ports in the group that were 64 bytes in length
		(including FCS octets and excluding framing bits)
		and contained errors."
::= { groupOctetsEntry 7 }

gsobkt65to127Ok OBJECT-TYPE
      	SYNTAX  Counter
      	ACCESS  read-only
      	STATUS  mandatory
      	DESCRIPTION
	      	"The total number of packets received from all
		ports in the group that were between 65 bytes
		and 127 bytes in length inclusive (including FCS
		octets and excluding framing bits) and did not
		contain errors."
::= { groupOctetsEntry 8 }

gsobkt65to127Err OBJECT-TYPE
      	SYNTAX  Counter
      	ACCESS  read-only
      	STATUS  mandatory
      	DESCRIPTION
	      	"The total number of packets received from all
		ports in the group that were between 65 bytes
		and 127 bytes in length inclusive (including FCS
		octets and excluding framing bits) and contained
		errors."
::= { groupOctetsEntry 9 }

gsobkt128to255Ok OBJECT-TYPE
      	SYNTAX  Counter
      	ACCESS  read-only
      	STATUS  mandatory
      	DESCRIPTION
	      	"The total number of packets received from all
		ports in the group that were between 128 bytes 
		and 255 bytes in length inclusive (including FCS
		octets and excluding framing bits) and did not
		contain errors."
::= { groupOctetsEntry 10 }

gsobkt128to255Err OBJECT-TYPE
      	SYNTAX  Counter
      	ACCESS  read-only
      	STATUS  mandatory
      	DESCRIPTION
	      	"The total number of packets received from all
		ports in the group that were between 128 bytes 
		and 255 bytes in length inclusive (including FCS
		octets and excluding framing bits) and contained
		errors."
::= { groupOctetsEntry 11 }

gsobkt256to511Ok OBJECT-TYPE
      	SYNTAX  Counter
      	ACCESS  read-only
      	STATUS  mandatory
      	DESCRIPTION
	      	"The total number of packets received from all
		ports in the group that were between 256 bytes
		and 511 bytes in length inclusive (including FCS
		octets and excluding framing bits) and did not
		contain errors."
::= { groupOctetsEntry 12 }

gsobkt256to511Err OBJECT-TYPE
      	SYNTAX  Counter
      	ACCESS  read-only
      	STATUS  mandatory
      	DESCRIPTION
	      	"The total number of packets received from all
		ports in the group that were between 256 bytes
		and 511 bytes in length inclusive (including FCS
		octets and excluding framing bits) and contained
		errors."
::= { groupOctetsEntry 13 }

gsobkt512to1023Ok OBJECT-TYPE
      	SYNTAX  Counter
      	ACCESS  read-only
      	STATUS  mandatory
      	DESCRIPTION
	      	"The total number of packets received from all
		ports in the group that were between 512 bytes 
		and 1023 bytes in length inclusive (including FCS
		octets and excluding framing bits) and did not
		contain errors."
::= { groupOctetsEntry 14 }

gsobkt512to1023Err OBJECT-TYPE
      	SYNTAX  Counter
      	ACCESS  read-only
      	STATUS  mandatory
      	DESCRIPTION
	      	"The total number of packets received from all
		ports in the group that were between 512 bytes 
		and 1023 bytes in length inclusive (including FCS
		octets and excluding framing bits) and contained
		errors."
::= { groupOctetsEntry 15 }

gsobkt1024to1518Ok OBJECT-TYPE
      	SYNTAX  Counter
      	ACCESS  read-only
      	STATUS  mandatory
      	DESCRIPTION
	      	"The total number of packets received from all
		ports in the group that were between 1024 bytes
		and 1518 bytes in length inclusive (including FCS
		octets and excluding framing bits) and did not
		contain errors."
::= { groupOctetsEntry 16 }

gsobkt1024to1518Err OBJECT-TYPE
      	SYNTAX  Counter
      	ACCESS  read-only
      	STATUS  mandatory
      	DESCRIPTION
	      	"The total number of packets received from all
		ports in the group that were between 1024 bytes 
		and 1518 bytes in length inclusive (including FCS
		octets and excluding framing bits) and contained
		errors."
::= { groupOctetsEntry 17 }

gsoRuntPacketsOk OBJECT-TYPE
      	SYNTAX  Counter
      	ACCESS  read-only
      	STATUS  mandatory
      	DESCRIPTION
	      	"The total number of packets received from all
		ports in the group that were less than 64 bytes,
		and did not contain any other errors."
::= { groupOctetsEntry 18 }

gsoRuntPacketsErr OBJECT-TYPE
      	SYNTAX  Counter
      	ACCESS  read-only
      	STATUS  mandatory
      	DESCRIPTION
	      	"The total number of packets reveived from all
		ports in the group that were less than 64 bytes
		and contained errors."
::= { groupOctetsEntry 19 }

gsoPacketsTooBigOk OBJECT-TYPE
      	SYNTAX  Counter
      	ACCESS  read-only
      	STATUS  mandatory
      	DESCRIPTION
	      	"The total number of packets reveived from all
		ports in the group that were larger than 1518 bytes,
		and did not contain any other errors."
::= { groupOctetsEntry 20 }

gsoPacketsTooBigErr OBJECT-TYPE
      	SYNTAX  Counter
      	ACCESS  read-only
      	STATUS  mandatory
      	DESCRIPTION
	      	"The total number of packets reveived from all
		ports in the group that were larger than 1518 bytes,
		and contained other errors."
::= { groupOctetsEntry 21 }


--
-- Extra IN3000 Group Level Packet Statistics 

groupPacketTable OBJECT-TYPE
     	SYNTAX  SEQUENCE OF GroupPacketEntry
      	ACCESS  not-accessible
      	STATUS  mandatory
      	DESCRIPTION
		"This table contains Repeater Group Level Packet
		Statistics."
::= { in3000StatsGroup 2 }

groupPacketEntry OBJECT-TYPE
	SYNTAX  GroupPacketEntry
      	ACCESS  not-accessible
     	STATUS  mandatory
      	DESCRIPTION
	      	"Each row of this table is associated to a TP3000
		or RP3000. Note the the groups are numbered from
		1 to 4."
      	INDEX   { gspGroupIndex }
::= { groupPacketTable 1 }

GroupPacketEntry ::=
      	SEQUENCE {
	  gspGroupIndex
	    INTEGER,
          gspPacketsRxOk 
            Counter,
          gspPacketsRxErr 
            Counter,
          gspPhysicalOk 
            Counter,
          gspPhysicalErr 
            Counter,
          gspMulticastOk 
            Counter,
          gspMulticastErr 
            Counter,
          gspBroadcastOk 
            Counter,
          gspBroadcastErr 
            Counter,
          gspHostPhysicalOk 
            Counter,
          gspHostPhysicalErr 
            Counter
       	}

gspGroupIndex OBJECT-TYPE
      	SYNTAX  INTEGER
      	ACCESS  read-only
      	STATUS  mandatory
      	DESCRIPTION
	      	"A unique value to the group. The groups are numbered
		from 1 to 4. The addresses set via the dip switches
		on the TP3000 and RP3000 are numbered 0 to 3. In
		order to calculate the group number add one (1) to
		the address set via the dip switches."
::= { groupPacketEntry 1 }

gspPacketsRxOk  OBJECT-TYPE
      	SYNTAX  Counter
      	ACCESS  read-only
      	STATUS  mandatory
      	DESCRIPTION
	      	"The total number of packet received by all ports
		in the group that were valid packets."
::= { groupPacketEntry 2 }

gspPacketsRxErr OBJECT-TYPE
      	SYNTAX  Counter
      	ACCESS  read-only
      	STATUS  mandatory
      	DESCRIPTION
	      	"The total number of packet received by all ports
		in the group that were packets with errors."
::= { groupPacketEntry 3 }

gspPhysicalOk OBJECT-TYPE
      	SYNTAX  Counter
      	ACCESS  read-only
      	STATUS  mandatory
      	DESCRIPTION
		"The total number of packets received from all
		ports in the group that were unicast packets
		and were valid packets."
::= { groupPacketEntry 4 }

gspPhysicalErr OBJECT-TYPE
      	SYNTAX  Counter
      	ACCESS  read-only
      	STATUS  mandatory
      	DESCRIPTION
		"The total number of packets received from all
		ports in the group that were unicast packets
		and were packets with errors."
::= { groupPacketEntry 5 }

gspMulticastOk OBJECT-TYPE
      	SYNTAX  Counter
      	ACCESS  read-only
      	STATUS  mandatory
      	DESCRIPTION
		"The total number of packets received from all
		ports in the group that were multicast packets
		and were valid packets."
::= { groupPacketEntry 6 }

gspMulticastErr OBJECT-TYPE
      	SYNTAX  Counter
      	ACCESS  read-only
      	STATUS  mandatory
      	DESCRIPTION
		"The total number of packets received from all
		ports in the group that were multicast packets
		and were packets with errors."
::= { groupPacketEntry 7 }

gspBroadcastOk OBJECT-TYPE
      	SYNTAX  Counter
      	ACCESS  read-only
      	STATUS  mandatory
      	DESCRIPTION
	      	"The total number of packets received from all
		ports in the group that were broadcast packets
		and were valid packets."
::= { groupPacketEntry 8 }

gspBroadcastErr OBJECT-TYPE
      	SYNTAX  Counter
      	ACCESS  read-only
      	STATUS  mandatory
      	DESCRIPTION
	      	"The total number of packets received from all
		ports in the group that were broadcast packets
		and were packets with errors."
::= { groupPacketEntry 9 }

gspHostPhysicalOk OBJECT-TYPE
      	SYNTAX  Counter
      	ACCESS  read-only
      	STATUS  mandatory
      	DESCRIPTION
	      	"The total number of packets received from all
		ports in the group that were unicast packets,
		addressed to the IN3000 and did not have errors."
::= { groupPacketEntry 10 }

gspHostPhysicalErr OBJECT-TYPE
      	SYNTAX  Counter
      	ACCESS  read-only
      	STATUS  mandatory
      	DESCRIPTION
	      	"The total number of packets received from all
		ports in the group that were unicast packets,
		addressed to the IN3000 and had errors."
::= { groupPacketEntry 11 }


--
-- Extra IN3000 Group Level Statistics 

groupMiscTable OBJECT-TYPE
     	SYNTAX  SEQUENCE OF GroupMiscEntry
      	ACCESS  not-accessible
      	STATUS  mandatory
      	DESCRIPTION
		"This table contains Repeater Group Level
		Statistics."
::= { in3000StatsGroup 3 }

groupMiscEntry OBJECT-TYPE
	SYNTAX  GroupMiscEntry
      	ACCESS  not-accessible
     	STATUS  mandatory
      	DESCRIPTION
	      	"Each row of this table is associated to a TP3000
		or RP3000. Note the the groups are numbered from
		1 to 4."
      	INDEX   { gsmGroupIndex }
::= { groupMiscTable 1 }

GroupMiscEntry ::=
      	SEQUENCE {
	  gsmGroupIndex
	    INTEGER,
	  gsmNumPorts
	    INTEGER,
	  gsmName
	    DisplayString,
	  gsmType
	    INTEGER,
	  gsmNumLinkUp
	    Gauge,
	  gsmNumLinkPulses
	    Gauge,
          gsmCollisions 
            Counter,
          gsmLateCollisions 
            Counter,
          gsmPartitions 
            Counter,
          gsmJabbers 
            Counter,
          gsmShortFragments 
            Counter,
          gsmCrcFae 
            Counter,
          gsmCrc 
            Counter,
          gsmFifoOverrun 
            Counter,
          gsmDeferring
            Counter
       	}

gsmGroupIndex OBJECT-TYPE
      	SYNTAX  INTEGER
      	ACCESS  read-only
      	STATUS  mandatory
      	DESCRIPTION
	      	"A unique value to the group. The groups are numbered
		from 1 to 4. The addresses set via the dip switches
		on the TP3000 and RP3000 are numbered 0 to 3. In
		order to calculate the group number add one (1) to
		the address set via the dip switches."
::= { groupMiscEntry 1 }

gsmNumPorts OBJECT-TYPE
      	SYNTAX  INTEGER
      	ACCESS  read-only
      	STATUS  mandatory
      	DESCRIPTION
	      	"The total number of ports contained in the group."
::= { groupMiscEntry 2 }

gsmName OBJECT-TYPE
      	SYNTAX  DisplayString (SIZE(0..25))
      	ACCESS  read-write
      	STATUS  mandatory
      	DESCRIPTION
	      	"The name of the group."
::= { groupMiscEntry 3 }

gsmType OBJECT-TYPE
      	SYNTAX  INTEGER
      	{
          tp3000(1),
          rp3000(2),
          unknown(3)
      	}
      	ACCESS  read-only
      	STATUS  mandatory
      	DESCRIPTION
	      	"The microhub type."
::= { groupMiscEntry 4 }

gsmNumLinkUp OBJECT-TYPE
      	SYNTAX  Gauge
      	ACCESS  read-only
      	STATUS  mandatory
      	DESCRIPTION
	      	"The total number of ports in the group that have
		link status."
::= { groupMiscEntry 5 }

gsmNumLinkPulses OBJECT-TYPE
      	SYNTAX  Gauge
      	ACCESS  read-only
      	STATUS  mandatory
      	DESCRIPTION
	      	"The total number of ports in the group that have
		link pulses enabled."
::= { groupMiscEntry 6 }

gsmCollisions OBJECT-TYPE
      	SYNTAX  Counter
      	ACCESS  read-only
      	STATUS  mandatory
      	DESCRIPTION
	      	"The total number of collisions detected by all
		ports in the group."
::= { groupMiscEntry 7 }

gsmLateCollisions OBJECT-TYPE
      	SYNTAX  Counter
      	ACCESS  read-only
      	STATUS  mandatory
      	DESCRIPTION
	      	"The total number of late collisions detected by
		all ports in the group."
::= { groupMiscEntry 8 }

gsmPartitions OBJECT-TYPE
      	SYNTAX  Counter
      	ACCESS  read-only
      	STATUS  mandatory
      	DESCRIPTION
	      	"The total number of partitions from all ports in the
		group."
::= { groupMiscEntry 9 }

gsmJabbers OBJECT-TYPE
      	SYNTAX  Counter
      	ACCESS  read-only
      	STATUS  mandatory
      	DESCRIPTION
	      	"The total number of frames from all port in the
		group that were longer than 1518 bytes, and
		had a non integral number of bytes or a bad
		frame check sequence (FCS)."
::= { groupMiscEntry 10 }

gsmShortFragments OBJECT-TYPE
      	SYNTAX  Counter
      	ACCESS  read-only
      	STATUS  mandatory
      	DESCRIPTION
	      	"Total number of packets from all ports in the
		group that were less than 64 bytes, and had a
		non-integral number of octets or had a bad frame
		check sequence (FCS)."
::= { groupMiscEntry 11 }

gsmCrcFae OBJECT-TYPE
      	SYNTAX  Counter
      	ACCESS  read-only
      	STATUS  mandatory
      	DESCRIPTION
	      	"The total number of packets reveived from all
		ports in the group that had frame alignment errors.
		Since there was a frame alignment error the packet
		also had a bad CRC."
::= { groupMiscEntry 12 }

gsmCrc OBJECT-TYPE
      	SYNTAX  Counter
      	ACCESS  read-only
      	STATUS  mandatory
      	DESCRIPTION
	      	"The total number of packets received from all
		ports in the group that did not have a frame alignment
		error, but they had a bad CRC."
::= { groupMiscEntry 13 }

gsmFifoOverrun OBJECT-TYPE
      	SYNTAX  Counter
      	ACCESS  read-only
      	STATUS  mandatory
      	DESCRIPTION
	      	"The total number of packets reveived from all port
		in the group that caused the ethernet controlled to
		overrun its FIFO."
::= { groupMiscEntry 14 }

gsmDeferring OBJECT-TYPE
      	SYNTAX  Counter
      	ACCESS  read-only
      	STATUS  mandatory
      	DESCRIPTION
	      	"The total number of packets from all ports in the
		group that caused the ethernet controller to detect
		a jabber."
::= { groupMiscEntry 15 }


--
-- Extra IN3000 Group Level Statistics
--
--

in3000StatsPort        OBJECT IDENTIFIER ::= { in3000 7 }

portOctetsTable OBJECT-TYPE
     	SYNTAX  SEQUENCE OF PortOctetsEntry
      	ACCESS  not-accessible
      	STATUS  mandatory
      	DESCRIPTION
		"This table contains octet statistics that deal with
		the TP3000 and RP3000 ports."
::= { in3000StatsPort 1 }

portOctetsEntry OBJECT-TYPE
	SYNTAX  PortOctetsEntry
      	ACCESS  not-accessible
     	STATUS  mandatory
      	DESCRIPTION
	      	"Each row in this table is associated with a port
		in a TP3000 or RP3000. Note that groups are numbered
		1 to 4 and ports are numbered 1 to 7.

		The row instance is made up of the group number
		and the port number."
      	INDEX   { psoGroupIndex, psoPortIndex }
::= { portOctetsTable 1 }

PortOctetsEntry ::=
      	SEQUENCE {
	  psoGroupIndex
	    INTEGER, 
	  psoPortIndex
	    INTEGER,
          psoHostOctetsRxOk
            Counter,
          psoHostOctetsRxErr
            Counter,
          psoOctetsRxOk
            Counter,
          psoOctetsRxErr
            Counter,
          psobkt64Ok 
            Counter,
          psobkt64Err 
            Counter,
          psobkt65to127Ok 
            Counter,
          psobkt65to127Err 
            Counter,
          psobkt128to255Ok 
            Counter,
          psobkt128to255Err 
            Counter,
          psobkt256to511Ok 
            Counter,
          psobkt256to511Err 
            Counter,
          psobkt512to1023Ok 
            Counter,
          psobkt512to1023Err 
            Counter,
          psobkt1024to1518Ok 
            Counter,
          psobkt1024to1518Err 
            Counter,
          psoRuntPacketsOk 
            Counter,
          psoRuntPacketsErr 
            Counter,
          psoPacketsTooBigOk 
            Counter,
          psoPacketsTooBigErr 
            Counter
        }

psoGroupIndex OBJECT-TYPE
      	SYNTAX  INTEGER
      	ACCESS  read-only
      	STATUS  mandatory
      	DESCRIPTION
	      	"The group that this port resides in. The groups
		are numbered 1 to 4."
::= { portOctetsEntry 1 }

psoPortIndex OBJECT-TYPE
      	SYNTAX  INTEGER
      	ACCESS  read-only
      	STATUS  mandatory
      	DESCRIPTION
	      	"The port number of this port. Note that the ports
		are numbered 1 to 7. For the TP3000 the twisted
		pair ports are numbered 1 to 6 and the remaining
		ethernet port (either 10base2 or AUI) is port 7."
::= { portOctetsEntry 2 }

psoHostOctetsRxOk OBJECT-TYPE
      	SYNTAX  Counter
      	ACCESS  read-only
      	STATUS  mandatory
      	DESCRIPTION
	      	"The total number of octets received on this port
		that were from packets without errors and were
		addressed to the IN3000."
::= { portOctetsEntry 3 }

psoHostOctetsRxErr OBJECT-TYPE
      	SYNTAX  Counter
      	ACCESS  read-only
      	STATUS  mandatory
      	DESCRIPTION
	      	"The total number of octets received on this port
		that were from packets with errors and were
		addressed to the IN3000."
::= { portOctetsEntry 4 }

psoOctetsRxOk OBJECT-TYPE
      	SYNTAX  Counter
      	ACCESS  read-only
      	STATUS  mandatory
      	DESCRIPTION
	      	"The total number of octets received on this port
		that were from packets without errors."
::= { portOctetsEntry 5 }

psoOctetsRxErr OBJECT-TYPE
      	SYNTAX  Counter
      	ACCESS  read-only
      	STATUS  mandatory
      	DESCRIPTION
	      	"The total number of octets received on this port
		that were from packets with errors."
::= { portOctetsEntry 6 }

psobkt64Ok OBJECT-TYPE
      	SYNTAX  Counter
      	ACCESS  read-only
      	STATUS  mandatory
      	DESCRIPTION
	      	"The total number of packets receive by this port
		that were 64 bytes in length (including FCS octets
		and excluding framing bits) and did not contain
		errors."
::= { portOctetsEntry 7 }

psobkt64Err OBJECT-TYPE
      	SYNTAX  Counter
      	ACCESS  read-only
      	STATUS  mandatory
      	DESCRIPTION
	      	"The total number of packets receive by this port
		that were 64 bytes in length (including FCS octets
		and excluding framing bits) and contained
		errors."
::= { portOctetsEntry 8 }

psobkt65to127Ok OBJECT-TYPE
      	SYNTAX  Counter
      	ACCESS  read-only
      	STATUS  mandatory
      	DESCRIPTION
	      	"The total number of packets receive by this port
		that were between 65 and 127 bytes in length
		inclusive (including FCS octets	and excluding
		framing bits) and did not contain errors."
::= { portOctetsEntry 9 }

psobkt65to127Err OBJECT-TYPE
      	SYNTAX  Counter
      	ACCESS  read-only
      	STATUS  mandatory
      	DESCRIPTION
	      	"The total number of packets receive by this port
		that were between 65 and 127 bytes in length
		inclusive (including FCS octets	and excluding
		framing bits) and contained errors."
::= { portOctetsEntry 10 }

psobkt128to255Ok OBJECT-TYPE
      	SYNTAX  Counter
      	ACCESS  read-only
      	STATUS  mandatory
      	DESCRIPTION
	      	"The total number of packets receive by this port
		that were between 128 and 255 bytes in length
		inclusive (including FCS octets	and excluding
		framing bits) and did not contain errors."
::= { portOctetsEntry 11 }

psobkt128to255Err OBJECT-TYPE
      	SYNTAX  Counter
      	ACCESS  read-only
      	STATUS  mandatory
      	DESCRIPTION
	      	"The total number of packets receive by this port
		that were between 128 and 255 bytes in length
		inclusive (including FCS octets	and excluding
		framing bits) and contained errors."
::= { portOctetsEntry 12 }

psobkt256to511Ok OBJECT-TYPE
      	SYNTAX  Counter
      	ACCESS  read-only
      	STATUS  mandatory
      	DESCRIPTION
	      	"The total number of packets receive by this port
		that were between 256 and 511 bytes in length
		inclusive (including FCS octets	and excluding
		framing bits) and did not contain errors."
::= { portOctetsEntry 13 }

psobkt256to511Err OBJECT-TYPE
      	SYNTAX  Counter
      	ACCESS  read-only
      	STATUS  mandatory
      	DESCRIPTION
	      	"The total number of packets receive by this port
		that were between 256 and 511 bytes in length
		inclusive (including FCS octets	and excluding
		framing bits) and contained errors."
::= { portOctetsEntry 14 }

psobkt512to1023Ok OBJECT-TYPE
      	SYNTAX  Counter
      	ACCESS  read-only
      	STATUS  mandatory
      	DESCRIPTION
	      	"The total number of packets receive by this port
		that were between 512 and 1023 bytes in length
		inclusive (including FCS octets	and excluding
		framing bits) and did not contain errors."
::= { portOctetsEntry 15 }

psobkt512to1023Err OBJECT-TYPE
      	SYNTAX  Counter
      	ACCESS  read-only
      	STATUS  mandatory
      	DESCRIPTION
	      	"The total number of packets receive by this port
		that were between 512 and 1023 bytes in length
		inclusive (including FCS octets	and excluding
		framing bits) and contained errors."
::= { portOctetsEntry 16 }

psobkt1024to1518Ok OBJECT-TYPE
      	SYNTAX  Counter
      	ACCESS  read-only
      	STATUS  mandatory
      	DESCRIPTION
	      	"The total number of packets receive by this port
		that were between 1024 and 1518 bytes in length
		inclusive (including FCS octets	and excluding
		framing bits) and did not contain errors."
::= { portOctetsEntry 17 }

psobkt1024to1518Err OBJECT-TYPE
      	SYNTAX  Counter
      	ACCESS  read-only
      	STATUS  mandatory
      	DESCRIPTION
	      	"The total number of packets receive by this port
		that were between 1024 and 1518 bytes in length
		inclusive (including FCS octets	and excluding
		framing bits) and contained errors."
::= { portOctetsEntry 18 }

psoRuntPacketsOk OBJECT-TYPE
      	SYNTAX  Counter
      	ACCESS  read-only
      	STATUS  mandatory
      	DESCRIPTION
	      	"The total number of packets received by this port
		that were less than 64 bytes, but contained no
		other errors."
::= { portOctetsEntry 19 }

psoRuntPacketsErr OBJECT-TYPE
      	SYNTAX  Counter
      	ACCESS  read-only
      	STATUS  mandatory
      	DESCRIPTION
	      	"The total number of packets received by this port
		that were less than 64 bytes, and contained other
		errors."
::= { portOctetsEntry 20 }

psoPacketsTooBigOk OBJECT-TYPE
      	SYNTAX  Counter
      	ACCESS  read-only
      	STATUS  mandatory
      	DESCRIPTION
	      	"The total number of packets received by this port
		that were greater than 1518 bytes, but contained
		no other errors."
::= { portOctetsEntry 21 }

psoPacketsTooBigErr OBJECT-TYPE
      	SYNTAX  Counter
      	ACCESS  read-only
      	STATUS  mandatory
      	DESCRIPTION
	      	"The total number of packets received by this port
		that were greater than 1518 bytes, and contained
		other errors."
::= { portOctetsEntry 22 }


--
-- Port level packet stats
--

portPacketTable OBJECT-TYPE
     	SYNTAX  SEQUENCE OF PortPacketEntry
      	ACCESS  not-accessible
      	STATUS  mandatory
      	DESCRIPTION
		"This table contains statistics that deal with
		the TP3000 and RP3000 ports."
::= { in3000StatsPort 2 }

portPacketEntry OBJECT-TYPE
	SYNTAX  PortPacketEntry
      	ACCESS  not-accessible
     	STATUS  mandatory
      	DESCRIPTION
	      	"Each row in this table is associated with a port
		in a TP3000 or RP3000. Note that groups are numbered
		1 to 4 and ports are numbered 1 to 7.

		The row instance is made up of the group number
		and the port number."
      	INDEX   { pspGroupIndex, pspPortIndex }
::= { portPacketTable 1 }

PortPacketEntry ::=
      	SEQUENCE {
	  pspGroupIndex
	    INTEGER, 
	  pspPortIndex
	    INTEGER,
          pspPacketsRxOk 
            Counter,
          pspPacketsRxErr 
            Counter,
          pspPhysicalOk 
            Counter,
          pspPhysicalErr 
            Counter,
          pspMulticastOk 
            Counter,
          pspMulticastErr 
            Counter,
          pspBroadcastOk 
            Counter,
          pspBroadcastErr 
            Counter,
          pspHostPhysicalOk 
            Counter,
          pspHostPhysicalErr 
            Counter
      	}

pspGroupIndex OBJECT-TYPE
      	SYNTAX  INTEGER
      	ACCESS  read-only
      	STATUS  mandatory
      	DESCRIPTION
	      	"The group that this port resides in. The groups
		are numbered 1 to 4."
::= { portPacketEntry 1 }

pspPortIndex OBJECT-TYPE
      	SYNTAX  INTEGER
      	ACCESS  read-only
      	STATUS  mandatory
      	DESCRIPTION
	      	"The port number of this port. Note that the ports
		are numbered 1 to 7. For the TP3000 the twisted
		pair ports are numbered 1 to 6 and the remaining
		ethernet port (either 10base2 or AUI) is port 7."
::= { portPacketEntry 2 }

pspPacketsRxOk  OBJECT-TYPE
      	SYNTAX  Counter
      	ACCESS  read-only
      	STATUS  mandatory
      	DESCRIPTION
	      	"The total number of packets received on this
		port that did no have any errors."
::= { portPacketEntry 3 }

pspPacketsRxErr OBJECT-TYPE
      	SYNTAX  Counter
      	ACCESS  read-only
      	STATUS  mandatory
      	DESCRIPTION
	      	"The total number of packets received on this
		port that had errors."
::= { portPacketEntry 4 }

pspPhysicalOk OBJECT-TYPE
      	SYNTAX  Counter
      	ACCESS  read-only
      	STATUS  mandatory
      	DESCRIPTION
	      	"The total number of unicast packets received on
		this port that did not have any errors."
::= { portPacketEntry 5 }

pspPhysicalErr OBJECT-TYPE
      	SYNTAX  Counter
      	ACCESS  read-only
      	STATUS  mandatory
      	DESCRIPTION
	      	"The total number of unicast packets received on
		this port that had errors."
::= { portPacketEntry 6 }

pspMulticastOk OBJECT-TYPE
      	SYNTAX  Counter
      	ACCESS  read-only
      	STATUS  mandatory
      	DESCRIPTION
	      	"The total number of multicast packets received on
		this port that did no have any errors."
::= { portPacketEntry 7 }

pspMulticastErr OBJECT-TYPE
      	SYNTAX  Counter
      	ACCESS  read-only
      	STATUS  mandatory
      	DESCRIPTION
	      	"The total number of multicast packets received on
		this port that have errors."
::= { portPacketEntry 8 }

pspBroadcastOk OBJECT-TYPE
      	SYNTAX  Counter
      	ACCESS  read-only
      	STATUS  mandatory
      	DESCRIPTION
	      	"The total number of broadcast packets that were
		received by this port and had no errors."
::= { portPacketEntry 9 }

pspBroadcastErr OBJECT-TYPE
      	SYNTAX  Counter
      	ACCESS  read-only
      	STATUS  mandatory
      	DESCRIPTION
	      	"The total number of broadcast packets that were
		received by this port and had errors."
::= { portPacketEntry 10 }

pspHostPhysicalOk OBJECT-TYPE
      	SYNTAX  Counter
      	ACCESS  read-only
      	STATUS  mandatory
      	DESCRIPTION
	      	"The total number of unicast packets received by
		this port that were addressed to the IN3000 and had
		no errors."
::= { portPacketEntry 11 }

pspHostPhysicalErr OBJECT-TYPE
      	SYNTAX  Counter
      	ACCESS  read-only
      	STATUS  mandatory
      	DESCRIPTION
	      	"The total number of unicast packets received by
		this port that were addressed to the IN3000 and had
		errors."
::= { portPacketEntry 12 }

--
-- Misc. port stats
--

portMiscTable OBJECT-TYPE
     	SYNTAX  SEQUENCE OF PortMiscEntry
      	ACCESS  not-accessible
      	STATUS  mandatory
      	DESCRIPTION
		"This table contains statistics that deal with
		the TP3000 and RP3000 ports."
::= { in3000StatsPort 3 }

portMiscEntry OBJECT-TYPE
	SYNTAX  PortMiscEntry
      	ACCESS  not-accessible
     	STATUS  mandatory
      	DESCRIPTION
	      	"Each row in this table is associated with a port
		in a TP3000 or RP3000. Note that groups are numbered
		1 to 4 and ports are numbered 1 to 7.

		The row instance is made up of the group number
		and the port number."
      	INDEX   { psmGroupIndex, psmPortIndex }
::= { portMiscTable 1 }

PortMiscEntry ::=
      	SEQUENCE {
	  psmGroupIndex
	    INTEGER, 
	  psmPortIndex
	    INTEGER,
	  psmName
	    DislpayString,
	  psmType
	    INTEGER,
	  psmLinkState
	    INTEGER,
	  psmLinkPulses
	    INTEGER,
          psmCollisions 
            Counter,
          psmLateCollisions 
            Counter,
          psmPartitions 
            Counter,
          psmJabbers 
            Counter,
          psmShortFragments 
            Counter,
          psmCrcFae 
            Counter,
          psmCrc 
            Counter,
          psmFifoOverrun 
            Counter,
          psmDeferring
            Counter
      	}

psmGroupIndex OBJECT-TYPE
      	SYNTAX  INTEGER
      	ACCESS  read-only
      	STATUS  mandatory
      	DESCRIPTION
	      	"The group that this port resides in. The groups
		are numbered 1 to 4."
::= { portMiscEntry 1 }

psmPortIndex OBJECT-TYPE
      	SYNTAX  INTEGER
      	ACCESS  read-only
      	STATUS  mandatory
      	DESCRIPTION
	      	"The port number of this port. Note that the ports
		are numbered 1 to 7. For the TP3000 the twisted
		pair ports are numbered 1 to 6 and the remaining
		ethernet port (either 10base2 or AUI) is port 7."
::= { portMiscEntry 2 }

psmName OBJECT-TYPE
      	SYNTAX  DisplayString (SIZE(0..25))
      	ACCESS  read-write
      	STATUS  mandatory
      	DESCRIPTION
      		"The name assigned to this port."
::= { portMiscEntry 3 }

psmType OBJECT-TYPE
      	SYNTAX  INTEGER
      	{
          tenBaseT(1),
          aui-bnc(2),
          unknown(3)
      	}
      	ACCESS  read-only
      	STATUS  mandatory
      	DESCRIPTION
	      	"The port type."
::= { portMiscEntry 4 }

psmLinkState OBJECT-TYPE
      	SYNTAX  INTEGER
      	{
          up(1),
          down(2),
          unsupported(3)
      	}
      	ACCESS  read-only
      	STATUS  mandatory
      	DESCRIPTION
	      	"The link state of the port.

	      	Note that if link pulses are disabled then
	      	the link state will be up."	   
::= { portMiscEntry 5 }

psmLinkPulses OBJECT-TYPE
      	SYNTAX  INTEGER
      	{
	  enable(1),
	  disable(2),
	  unsupported(3)
      	}
      	ACCESS  read-write
      	STATUS  mandatory
      	DESCRIPTION
	      	"This variable is used to check or set whether
		this port has link pulses enabled."
::= { portMiscEntry 6 }


psmCollisions OBJECT-TYPE
      	SYNTAX  Counter
      	ACCESS  read-only
      	STATUS  mandatory
      	DESCRIPTION
	      	"The total number of collisions that were received
		by this port."
::= { portMiscEntry 7 }

psmLateCollisions OBJECT-TYPE
      	SYNTAX  Counter
      	ACCESS  read-only
      	STATUS  mandatory
      	DESCRIPTION
	      	"The total number of late collisions that were
		received by this port."
::= { portMiscEntry 8 }

psmPartitions OBJECT-TYPE
      	SYNTAX  Counter
      	ACCESS  read-only
      	STATUS  mandatory
      	DESCRIPTION
	      	"The total number of times this port entered the
		partitioned state."
::= { portMiscEntry 9 }

psmJabbers OBJECT-TYPE
      	SYNTAX  Counter
      	ACCESS  read-only
      	STATUS  mandatory
      	DESCRIPTION
	      	"The total number of frames received by this port
		that were longer than 1518 bytes, and had a non-
		integral number of octets or had a bad frame check
		sequence (FCS)."
::= { portMiscEntry 10 }

psmShortFragments OBJECT-TYPE
      	SYNTAX  Counter
      	ACCESS  read-only
      	STATUS  mandatory
      	DESCRIPTION
	      	"The total number of frames received by this port
		that were less than 64 bytes, and had a non-
		integral number of octets or had a bad frame check
		sequence (FCS)."
::= { portMiscEntry 11 }

psmCrcFae OBJECT-TYPE
      	SYNTAX  Counter
      	ACCESS  read-only
      	STATUS  mandatory
      	DESCRIPTION
	      	"The total number of packets reveived by this port
		that had frame alignment errors. Since there was a
		frame alignment error the packet also had a bad CRC."
::= { portMiscEntry 12 }

psmCrc OBJECT-TYPE
      	SYNTAX  Counter
      	ACCESS  read-only
      	STATUS  mandatory
      	DESCRIPTION
	      	"The total number of packets reveived by this port
		that did not have frame alignment errors but had a
		bad CRC."
::= { portMiscEntry 13 }

psmFifoOverrun OBJECT-TYPE
      	SYNTAX  Counter
      	ACCESS  read-only
      	STATUS  mandatory
      	DESCRIPTION
	      	"The total number of packets reveived by this port
		that caused the ethernet controlled to overrun its
		FIFO."
::= { portMiscEntry 14 }

psmDeferring OBJECT-TYPE
      	SYNTAX  Counter
      	ACCESS  read-only
      	STATUS  mandatory
      	DESCRIPTION
	      	"The total number of packets received by this
		port the caused the ethernet controller to detect
		a jabber."
::= { portMiscEntry 15 }


--
-- memory stats
--
in3000StatsMemory OBJECT IDENTIFIER ::= { in3000 8 }

initHeapSize OBJECT-TYPE
	SYNTAX	INTEGER
	ACCESS 	read-only
	STATUS	mandatory
	DESCRIPTION
		"The initial heap memory size in bytes."
::= { in3000StatsMemory 1 }

usedHeap OBJECT-TYPE
	SYNTAX	Gauge
	ACCESS 	read-only
	STATUS	mandatory
	DESCRIPTION
		"Amount of heap memory in use in bytes."
::= { in3000StatsMemory 2 }

freeHeap OBJECT-TYPE
	SYNTAX	Gauge
	ACCESS 	read-only
	STATUS	mandatory
	DESCRIPTION
		"Amount of free heap memory in bytes."
::= { in3000StatsMemory 3 }

heapStatus OBJECT-TYPE
	SYNTAX	INTEGER
	{
	  ok(1),
	  notOk(2)
	}
	ACCESS 	read-only
	STATUS	mandatory
	DESCRIPTION
		"The status of the heap. A notOk(2) response
		means the heap has been corrupted, and an ok(1)
		reponse means the heap is OK.

		The heap check is preformed at the time of memory
		coalescing and not on demand. Therefore, the value
		of the variable may not match the current state of
		the heap. If you wish to have the heap checked on
		demand please use the heapTest variable to preform
		this test."
::= { in3000StatsMemory 4 }

mallocCalls OBJECT-TYPE
	SYNTAX	Counter
	ACCESS 	read-only
	STATUS	mandatory
	DESCRIPTION
		"Number of times malloc() has been called."
::= { in3000StatsMemory 5 }

reallocCalls OBJECT-TYPE
	SYNTAX	Counter
	ACCESS 	read-only
	STATUS	mandatory
	DESCRIPTION
		"Number of times realloc() has been called."
::= { in3000StatsMemory 6 }

callocCalls OBJECT-TYPE
	SYNTAX	Counter
	ACCESS 	read-only
	STATUS	mandatory
	DESCRIPTION
		"Number of times calloc() has been called."
::= { in3000StatsMemory 7 }

freeCalls OBJECT-TYPE
	SYNTAX	Counter
	ACCESS 	read-only
	STATUS	mandatory
	DESCRIPTION
		"Number of times free() has been called."
::= { in3000StatsMemory 8 }

noMemoryAvailable OBJECT-TYPE
	SYNTAX	Counter
	ACCESS 	read-only
	STATUS	mandatory
	DESCRIPTION
		"The number of times that there was not enough
		memory to complete a memory allocation operation."
::= { in3000StatsMemory 9 }

mnodeCoalesces OBJECT-TYPE
	SYNTAX	Counter
	ACCESS 	read-only
	STATUS	mandatory
	DESCRIPTION
		"The number of times that the memory manager coalesced
		mnodes."
::= { in3000StatsMemory 10 }

coalesceMemCalls OBJECT-TYPE
	SYNTAX	Counter
	ACCESS 	read-only
	STATUS	mandatory
	DESCRIPTION
		"The number of times that the memory manager was called to
		coalesced mnodes."
::= { in3000StatsMemory 11 }

coalesceThreshold OBJECT-TYPE
      	SYNTAX  INTEGER
      	ACCESS  read-write
      	STATUS  mandatory
      	DESCRIPTION
	      	"This variable is used to set the number of free calls
	      	before coalescing memory.

		This change takes effect as soon as the variable is changed."
::= { in3000StatsMemory 12 }

--
-- extra icmp stats

in3000StatsIcmp   OBJECT IDENTIFIER ::= { in3000 9 }

inUnknownTypes OBJECT-TYPE
	SYNTAX	Counter
	ACCESS 	read-only
	STATUS	mandatory
	DESCRIPTION
		"Number of ICMP packets received with unknown type fields."
::= { in3000StatsIcmp 1 }

bufferPoolEmpty OBJECT-TYPE
	SYNTAX	Counter
	ACCESS 	read-only
	STATUS	mandatory
	DESCRIPTION
		"Number of times an ICMP packet was received
    		and there were not enough available buffers."
::= { in3000StatsIcmp 2 }

dataBufferTooSmall OBJECT-TYPE
	SYNTAX	Counter
	ACCESS 	read-only
	STATUS	mandatory
	DESCRIPTION
		"Number of times an ICMP packet was received and the
		data buffer was too small."
::= { in3000StatsIcmp 3 }

--
-- thread stats
--

in3000StatsOS OBJECT IDENTIFIER ::= { in3000 10 }

threadCreateReq OBJECT-TYPE
	SYNTAX	Counter
	ACCESS 	read-only
	STATUS	mandatory
	DESCRIPTION
		"The number of thread create requests."
::= { in3000StatsOS 1 }

threadCreateOk OBJECT-TYPE
	SYNTAX	Counter
	ACCESS 	read-only
	STATUS	mandatory
	DESCRIPTION
		"The number of successful thread creates."
::= { in3000StatsOS 2 }

threadCreateFail OBJECT-TYPE
	SYNTAX	Counter
	ACCESS 	read-only
	STATUS	mandatory
	DESCRIPTION
		"The number of unsuccessful thread creates."
::= { in3000StatsOS 3 }

threadTableFull OBJECT-TYPE
	SYNTAX	Counter
	ACCESS 	read-only
	STATUS	mandatory
	DESCRIPTION
		"The number of requests to create a thread that
        failed because the maximum number of threads were reached."
::= { in3000StatsOS 4 }

threadKill OBJECT-TYPE
	SYNTAX	Counter
	ACCESS 	read-only
	STATUS	mandatory
	DESCRIPTION
		"The number of threads that have been killed."
::= { in3000StatsOS 5 }

threadMaximum OBJECT-TYPE
	SYNTAX	INTEGER
	ACCESS 	read-write
	STATUS	mandatory
	DESCRIPTION
		"The maximum number of threads that may be created.

		The set will take effect the next time the IN3000
		is initialized."
::= { in3000StatsOS 6 }

defaultStackSize OBJECT-TYPE
	SYNTAX	INTEGER
	ACCESS 	read-write
	STATUS	mandatory
	DESCRIPTION
		"The default stack size (in bytes) for each thread.

		The set will take effect the next time the IN3000
		is initialized."
::= { in3000StatsOS 7 }

defaultTimeSlice OBJECT-TYPE
	SYNTAX	INTEGER
	ACCESS 	read-write
	STATUS	mandatory
	DESCRIPTION
		"The default time slice (in milliseconds) for each
		thread.

		The set will take effect the next time the IN3000
		is initialized. All newly created threads will get
 		the new time slice."
::= { in3000StatsOS 8 }

bogusInterrupts OBJECT-TYPE
	SYNTAX	Counter
	ACCESS 	read-only
	STATUS	mandatory
	DESCRIPTION
		"The total number of bogus interrupts."
::= { in3000StatsOS 9 }

divideError OBJECT-TYPE
	SYNTAX	Counter
	ACCESS 	read-only
	STATUS	mandatory
	DESCRIPTION
		"The total number of divide by zero error
		 interrupts."
::= { in3000StatsOS 10 }

singleStep OBJECT-TYPE
	SYNTAX	Counter
	ACCESS 	read-only
	STATUS	mandatory
	DESCRIPTION
		"The total number of single step interrupts."
::= { in3000StatsOS 11 }

breakpoint  OBJECT-TYPE
	SYNTAX	Counter
	ACCESS 	read-only
	STATUS	mandatory
	DESCRIPTION
		"The total number of break point interrupts."
::= { in3000StatsOS 12 }

interruptOverflow OBJECT-TYPE
	SYNTAX	Counter
	ACCESS 	read-only
	STATUS	mandatory
	DESCRIPTION
		"The total number of interrupt overflows."
::= { in3000StatsOS 13 }

arrayBoundsCheck OBJECT-TYPE
	SYNTAX	Counter
	ACCESS 	read-only
	STATUS	mandatory
	DESCRIPTIOB
		"The total number of array bound check interrupts."
::= { in3000StatsOS 14 }

invalidOpcode OBJECT-TYPE
	SYNTAX	Counter
	ACCESS 	read-only
	STATUS	mandatory
	DESCRIPTION
		"Th total number of invalid op code interrupts."
::= { in3000StatsOS 15 }

escapeOpcode OBJECT-TYPE
	SYNTAX	Counter
	ACCESS 	read-only
	STATUS	mandatory
	DESCRIPTION
		"The total number of escape opcode interrupts."
::= { in3000StatsOS 16 }

coprocessorFault OBJECT-TYPE
	SYNTAX	Counter
	ACCESS 	read-only
	STATUS	mandatory
	DESCRIPTION
		"Th total number of coprocessor fault interrupts."
::= { in3000StatsOS 17 }

threadTable OBJECT-TYPE
     	SYNTAX  SEQUENCE OF ThreadEntry
      	ACCESS  not-accessible
      	STATUS  mandatory
      	DESCRIPTION
		"A table containing the currently running
		threads."
::= { in3000StatsOS 18 }

threadEntry OBJECT-TYPE
	SYNTAX  ThreadEntry
      	ACCESS  not-accessible
     	STATUS  mandatory
      	DESCRIPTION
	      	"Information about a particular thread.

		The instance of the table entries is the
		tid."
      	INDEX   { tid }
::= { threadTable 1 }

ThreadEntry ::=
      	SEQUENCE {
	  tid
	    INTEGER,
	  name
	    DisplayString,
	  priority
	    INTEGER,
	  muxCount
	    INTEGER,
	  status
	    INTEGER,
          stackSize
	    INTEGER 
      	}

tid OBJECT-TYPE
SYNTAX  INTEGER 
ACCESS  read-only
STATUS  mandatory
DESCRIPTION
	"This is the thread identifier. This is the unique
	number assigned to a thread. This value is also the
	instance of the table row."
::= { threadEntry 1 }

name OBJECT-TYPE
SYNTAX  DisplayString (SIZE(1..32))  
ACCESS  read-only
STATUS  mandatory
DESCRIPTION
	"This is the thread's assigned name."
::= { threadEntry 2 }

priority OBJECT-TYPE
SYNTAX  INTEGER 
ACCESS  read-only
STATUS  mandatory
DESCRIPTION
	"This is the thread's priority."
::= { threadEntry 3 }

muxCount OBJECT-TYPE
SYNTAX  INTEGER 
ACCESS  read-only
STATUS  mandatory
DESCRIPTION
	"This is the thread's mutual exclusion Count."
::= { threadEntry 4 }

status OBJECT-TYPE
SYNTAX  INTEGER
        {
	  running(1),
          killed(2),
          queued(3),
          blocked(4),
	  dead(5)           
        }
ACCESS  read-only
STATUS  mandatory
DESCRIPTION
	"This is the thread's status at the time of the SNMP query."
::= { threadEntry 5 }

stackSize OBJECT-TYPE
SYNTAX  INTEGER 
ACCESS  read-only
STATUS  mandatory
DESCRIPTION
	"This is the thread's stack size."
::= { threadEntry 6 }

--
-- extra  arp stats
--

in3000StatsArp    OBJECT IDENTIFIER ::= { in3000 11 }

arpInReqs OBJECT-TYPE
	SYNTAX	Counter
	ACCESS 	read-only
	STATUS	mandatory
	DESCRIPTION
		"The number of received ARP requests."
::= { in3000StatsArp 1 }

arpInRpls OBJECT-TYPE
	SYNTAX	Counter
	ACCESS 	read-only
	STATUS	mandatory
	DESCRIPTION
		"The number of  ARP replies received."
::= { in3000StatsArp 2 }

arpOutReqs OBJECT-TYPE
	SYNTAX	Counter
	ACCESS 	read-only
	STATUS	mandatory
	DESCRIPTION
		"The number of ARP requests sent."
::= { in3000StatsArp 3 }

arpOutRpls OBJECT-TYPE
	SYNTAX	Counter
	ACCESS 	read-only
	STATUS	mandatory
	DESCRIPTION
		"The number of ARP replies sent."
::= { in3000StatsArp 4 }

arpGetReqs OBJECT-TYPE
	SYNTAX	Counter
	ACCESS 	read-only
	STATUS	mandatory
	DESCRIPTION
		"The number of ARP Get requests."
::= { in3000StatsArp 5 }

arpPutReqs OBJECT-TYPE
	SYNTAX	Counter
	ACCESS 	read-only
	STATUS	mandatory
	DESCRIPTION
		"The number of ARP Put requests."
::= { in3000StatsArp 6 }

arpDeadEntries OBJECT-TYPE
	SYNTAX	Counter
	ACCESS 	read-only
	STATUS	mandatory
	DESCRIPTION
		"The number of dead ARP entries."
::= { in3000StatsArp 7 }

arpCacheSize OBJECT-TYPE
	SYNTAX	INTEGER (1..200)
 	ACCESS 	read-write
	STATUS	mandatory
	DESCRIPTION
		"The maximum number of ARP cache entries.

		Changing this value will take place on next
		reboot."
::= { in3000StatsArp 8 }

arpEntryTimeout OBJECT-TYPE
	SYNTAX	INTEGER (15..60480) 
	ACCESS 	read-write
	STATUS	mandatory
	DESCRIPTION
		"The length of time (in seconds) that an
		ARP entry is stored. If an entry is not
		accessed within this time period the entry
		is purged.

		Changes to this take place immediately."
::= { in3000StatsArp 9 }

arpNumRetries OBJECT-TYPE
	SYNTAX	INTEGER  (1..50)
	ACCESS 	read-write
	STATUS	mandatory
	DESCRIPTION
		"The number of ARP request retries before
		giving up.

		Changes to this take place after next reboot."
::= { in3000StatsArp 10 }

arpReplyTimeout OBJECT-TYPE
	SYNTAX	INTEGER (1..65000)
	ACCESS 	read-write
	STATUS	mandatory
	DESCRIPTION
		"The length of time ARP waits for an ARP
		response.

		Changes to this take place immediately."
::= { in3000StatsArp 11 }

in3000StatsIp    OBJECT IDENTIFIER ::= { in3000 12 }

inHdrTooSmall OBJECT-TYPE
	SYNTAX	Counter
	ACCESS 	read-only
	STATUS	mandatory
	DESCRIPTION
		"The number of IP packets with headers too small. This
		is a subset of ipHdrErrors."
::= { in3000StatsIp 1 }

inHdrBadVersion OBJECT-TYPE
	SYNTAX	Counter
	ACCESS 	read-only
	STATUS	mandatory
	DESCRIPTION
		"The number of IP packets with Incrrect version information.
                 This is a subset of ipHdrErrors."
::= { in3000StatsIp 2 }

inHdrBadCheckSum OBJECT-TYPE
	SYNTAX	Counter
	ACCESS 	read-only
	STATUS	mandatory
	DESCRIPTION
		"The number of IP packets with invalid checksums. This
		is a subset of ipHdrErrors."
::= { in3000StatsIp 3 }

inHdrBadOption OBJECT-TYPE
	SYNTAX	Counter
	ACCESS 	read-only
	STATUS	mandatory
	DESCRIPTION
		"The number of IP packets with one or more incorrect options.
                This is a subset of ipHdrErrors."
::= { in3000StatsIp 4 }

inDataNotAllocated OBJECT-TYPE
	SYNTAX	Counter
	ACCESS 	read-only
	STATUS	mandatory
	DESCRIPTION
		"This is an internal error. This is a subset of inDiscards."
::= { in3000StatsIp 5 }

inNoPacketBuffers OBJECT-TYPE
	SYNTAX	Counter
	ACCESS 	read-only
	STATUS	mandatory
	DESCRIPTION
		"The number of IP packets received that had to be discarded
		due to lack of buffer space. This is a subset of inDiscards."
::= { in3000StatsIp 6 }

outNoPacketBuffers OBJECT-TYPE
	SYNTAX	Counter
	ACCESS 	read-only
	STATUS	mandatory
	DESCRIPTION
		"The number of IP packets that were to be sent but had
       		to be discarded due to lack of buffer space. This is a
		subset of outDiscards."
::= { in3000StatsIp 7 }

outBadTransmits OBJECT-TYPE
	SYNTAX	Counter
	ACCESS 	read-only
	STATUS	mandatory
	DESCRIPTION
		"The number of IP packets that could not be transmitted
		even though the packet was valid."
::= { in3000StatsIp 8 }

outAddrNotResolved OBJECT-TYPE
	SYNTAX	Counter
	ACCESS 	read-only
	STATUS	mandatory
	DESCRIPTION
		"The number of IP packets that could not be transmitted
		due to ARP failure. The address could not be resolved."
::= { in3000StatsIp 9 }

reasmTimeout OBJECT-TYPE
	SYNTAX	INTEGER
	ACCESS 	read-write
	STATUS	mandatory
	DESCRIPTION
		"The IP reasmebly timeout."
::= { in3000StatsIp 10 }


in3000StatsHmi    OBJECT IDENTIFIER ::= { in3000 13 }

hmiReqs OBJECT-TYPE
	SYNTAX	Counter
	ACCESS 	read-only
	STATUS	mandatory
	DESCRIPTION
		"The number of HMI requests received."
::= { in3000StatsHmi 1 }

hmiResp OBJECT-TYPE
	SYNTAX	Counter
	ACCESS 	read-only
	STATUS	mandatory
	DESCRIPTION
		"The number of HMI reresponses sent. This does
		not include acknowledgement frames."
::= { in3000StatsHmi 2 }

hmiError OBJECT-TYPE
	SYNTAX	Counter
	ACCESS 	read-only
	STATUS	mandatory
	DESCRIPTION
		"The number of errors that occured processing HMI
		requests."
::= { in3000StatsHmi 3 }

hmiAckOk OBJECT-TYPE
	SYNTAX	Counter
	ACCESS 	read-only
	STATUS	mandatory
	DESCRIPTION
		"The number of HMI Good Acknowledgements sent."
::= { in3000StatsHmi 4 }

hmiAckBad OBJECT-TYPE
	SYNTAX	Counter
	ACCESS 	read-only
	STATUS	mandatory
	DESCRIPTION
		"The number of HMI Bad Acknowledgements sent."
::= { in3000StatsHmi 5 }

hmiTrap OBJECT-TYPE
	SYNTAX	Counter
	ACCESS 	read-only
	STATUS	mandatory
	DESCRIPTION
		"The number of HMI traps sent."
::= { in3000StatsHmi 6 }

hmiIdReq OBJECT-TYPE
	SYNTAX	Counter
	ACCESS 	read-only
	STATUS	mandatory
	DESCRIPTION
		"The number of HMI ID requests sent."
::= { in3000StatsHmi 7 }

hmiGetInfoReq OBJECT-TYPE
	SYNTAX	Counter
	ACCESS 	read-only
	STATUS	mandatory
	DESCRIPTION
		"The number of HMI GET INFO requests sent."
::= { in3000StatsHmi 8 }

hmiSelftestReq OBJECT-TYPE
	SYNTAX	Counter
	ACCESS 	read-only
	STATUS	mandatory
	DESCRIPTION
		"The number of HMI SELFTEST requests sent."
::= { in3000StatsHmi 9 }

hmiPortEnableReq OBJECT-TYPE
	SYNTAX	Counter
	ACCESS 	read-only
	STATUS	mandatory
	DESCRIPTION
		"The number of HMI PORT ENABLE requests sent."
::= { in3000StatsHmi 10 }

hmiPortDisableReq OBJECT-TYPE
	SYNTAX	Counter
	ACCESS 	read-only
	STATUS	mandatory
	DESCRIPTION
		"The number of HMI PORT DISABLE requests sent."
::= { in3000StatsHmi 11 }

hmiStatusReq OBJECT-TYPE
	SYNTAX	Counter
	ACCESS 	read-only
	STATUS	mandatory
	DESCRIPTION
		"The number of HMI STATUS requests sent."
::= { in3000StatsHmi 12 }

hmiRepeaterReq OBJECT-TYPE
	SYNTAX	Counter
	ACCESS 	read-only
	STATUS	mandatory
	DESCRIPTION
		"The number of HMI REPEATER requests sent."
::= { in3000StatsHmi 13 }

hmiPortObjectsReq OBJECT-TYPE
	SYNTAX	Counter
	ACCESS 	read-only
	STATUS	mandatory
	DESCRIPTION
		"The number of HMI POR OBJECTS request sent."
::= { in3000StatsHmi 14 }

hmiPortChangesReq OBJECT-TYPE
	SYNTAX	Counter
	ACCESS 	read-only
	STATUS	mandatory
	DESCRIPTION
		"The number of HMI PORT CHANGES requests sent."
::= { in3000StatsHmi 15 }

hmiSelfTestStatReq OBJECT-TYPE
	SYNTAX	Counter
	ACCESS 	read-only
	STATUS	mandatory
	DESCRIPTION
		"The number of HMI SELF TEST STATUTS requests sent."
::= { in3000StatsHmi 16 }

hmiDebugOnReq OBJECT-TYPE
	SYNTAX	Counter
	ACCESS 	read-only
	STATUS	mandatory
	DESCRIPTION
		"The number of HMI DEBUG ON requests sent."
::= { in3000StatsHmi 17 }

hmiDebugOffReq OBJECT-TYPE
	SYNTAX	Counter
	ACCESS 	read-only
	STATUS	mandatory
	DESCRIPTION
		"The number of HMI DEBUG OFF requests sent."
::= { in3000StatsHmi 18 }

hmiGetInfoResp OBJECT-TYPE
	SYNTAX	Counter
	ACCESS 	read-only
	STATUS	mandatory
	DESCRIPTION
		"The number of HMI GET INFO responses sent."
::= { in3000StatsHmi 19 }

hmiSelfTestResp OBJECT-TYPE
	SYNTAX	Counter
	ACCESS 	read-only
	STATUS	mandatory
	DESCRIPTION
		"The number of HMI SELF TEST responses sent."
::= { in3000StatsHmi 20 }

hmiStatusResp OBJECT-TYPE
	SYNTAX	Counter
	ACCESS 	read-only
	STATUS	mandatory
	DESCRIPTION
		"The number of HMI STATUS responses sent."
::= { in3000StatsHmi 21 }

hmiRepeaterResp OBJECT-TYPE
	SYNTAX	Counter
	ACCESS 	read-only
	STATUS	mandatory
	DESCRIPTION
		"The number of HMI REPEATER responses sent."
::= { in3000StatsHmi 22 }

hmiPortObjectsResp OBJECT-TYPE
	SYNTAX	Counter
	ACCESS 	read-only
	STATUS	mandatory
	DESCRIPTION
		"The number of HMI PORT OBJECTS responses sent."
::= { in3000StatsHmi 23 }

hmiPortChangesResp OBJECT-TYPE
	SYNTAX	Counter
	ACCESS 	read-only
	STATUS	mandatory
	DESCRIPTION
		"The number of HMI PORT CHANGES responses sent."
::= { in3000StatsHmi 24 }

hmiSelfTestStatResp OBJECT-TYPE
	SYNTAX	Counter
	ACCESS 	read-only
	STATUS	mandatory
	DESCRIPTION
		"The number of HMI SLEF TEST STATUS responses sent."
::= { in3000StatsHmi 25 }

--
-- IN3000 Serial Port Information
--
in3000StatsUart    OBJECT IDENTIFIER ::= { in3000 14 }

uartInOctets OBJECT-TYPE
	SYNTAX	Counter
	ACCESS 	read-only
	STATUS	mandatory
	DESCRIPTION
		"The number of octets received by the UART driver."
::= { in3000StatsUart 1 }

uartOutOctets OBJECT-TYPE
	SYNTAX	Counter
	ACCESS 	read-only
	STATUS	mandatory
	DESCRIPTION
		"The number of octets sent by the UART driver."
::= { in3000StatsUart 2 }

uartInDelivers OBJECT-TYPE
	SYNTAX	Counter
	ACCESS 	read-only
	STATUS	mandatory
	DESCRIPTION
		"The number of octets received by the Uart and
		passed to upper layer protocol, such as HMI."
::= { in3000StatsUart 3 }

uartOutDelivers OBJECT-TYPE
	SYNTAX	Counter
	ACCESS 	read-only
	STATUS	mandatory
	DESCRIPTION
		"The number of bytes sent by the Uart there were
		from a higher level protocol, such as HMI."
::= { in3000StatsUart 4 }

uartBaudRate OBJECT-TYPE
	SYNTAX	INTEGER
	{
	  br1200(1200),
	  br2400(2400),
	  br4800(4800),
	  br9600(9600),
	  br19200(19200),
	  br38400(38400),
	  br57600(57600),
	  br115200(115200)
	}
	ACCESS 	read-only
	STATUS	mandatory
	DESCRIPTION
		"The baud rate of the serial port."
::= { in3000StatsUart 5 }

uartDataBits OBJECT-TYPE
	SYNTAX	INTEGER
	{
	  five(5),
	  six(6),
	  seven(7),
	  eight(8)
	}
	ACCESS 	read-write
	STATUS	mandatory
	DESCRIPTION
		"The the number of data bits used by the serial port."
::= { in3000StatsUart 6 }

uartStopBits OBJECT-TYPE
	SYNTAX	INTEGER
	{
	  one(1),
	  two(2)
	}
	ACCESS 	read-write
	STATUS	mandatory
	DESCRIPTION
		"The number of stop bits used by the serial port."
::= { in3000StatsUart 7 }

uartParity OBJECT-TYPE
	SYNTAX	INTEGER
	{
	  none(1),
	  even(2),
	  odd(3)
	}
	ACCESS 	read-write
	STATUS	mandatory
	DESCRIPTION
		"The data parity used by the serial port."
::= { in3000StatsUart 8 }

uartHandshaking OBJECT-TYPE
	SYNTAX	INTEGER
	{
	  disabled(1),
	  xonXoff(2),
	  rtsCts(3)
	}
	ACCESS 	read-write
	STATUS	mandatory
	DESCRIPTION
		"The handshaking used bu the serial port."
::= { in3000StatsUart 9 }

uartOverrunErrors OBJECT-TYPE
	SYNTAX	Counter
	ACCESS 	read-only
	STATUS	mandatory
	DESCRIPTION
		"The number of time the UART has overrun
		causing an error." 
::= { in3000StatsUart 10 }

uartParityErrors OBJECT-TYPE
	SYNTAX	Counter
	ACCESS 	read-only
	STATUS	mandatory
	DESCRIPTION
		"The number frames received from the UART
		that had parity errors."
::= { in3000StatsUart 11 }

uartFramingErrors OBJECT-TYPE
	SYNTAX	Counter
	ACCESS 	read-only
	STATUS	mandatory
	DESCRIPTION
		"The number frames received from the UART
		that had framing errors." 
::= { in3000StatsUart 12 }

uartBreakIndicators OBJECT-TYPE
	SYNTAX	Counter
	ACCESS 	read-only
	STATUS	mandatory
	DESCRIPTION
		"The number indicators received by the
		UART."
::= { in3000StatsUart 13 }

--
-- in3000 selftests
--

in3000SelfTests OBJECT IDENTIFIER ::= { in3000 15 }

dallasTest OBJECT-TYPE
	SYNTAX	INTEGER
	{
           testPass(1),
           testFailed(2),
           runTest(3)
	}
	ACCESS 	read-write
	STATUS	mandatory
	DESCRIPTION
		"This variable is used to run a diagnostic test on
		the Universal Clock.

		To run the test this variable must be set to
		runTest(3). Setting this to any other value will
		result in an error."
::= { in3000SelfTests 1 }

flashTest OBJECT-TYPE
	SYNTAX	INTEGER
	{
           testPass(1),
           testFailed(2),
           runTest(3)
	}
	ACCESS 	read-write
	STATUS	mandatory
	DESCRIPTION
		"This variable is used to run a diagnostic test on
		the Non-Volitile RAM.

		To run the test this variable must be set to
		runTest(3). Setting this to any other value will
		result in an error."
::= { in3000SelfTests 2 }

uartTest OBJECT-TYPE
	SYNTAX	INTEGER
	{
           testPass(1),
           testFailed(2),
           runTest(3)
	}
	ACCESS 	read-write
	STATUS	mandatory
	DESCRIPTION
		"This variable is used to run a diagnostic test on
		the serial port (UART).

		To run the test this variable must be set to
		runTest(3). Setting this to any other value will
		result in an error."
::= { in3000SelfTests 3 }

nicTest OBJECT-TYPE
	SYNTAX	INTEGER
	{
           testPass(1),
           testFailed(2),
           runTest(3)
	}
	ACCESS 	read-write
	STATUS	mandatory
	DESCRIPTION
		"This variable is used to run a diagnostic test on
		the ethernet controller.

		To run the test this variable must be set to
		runTest(3). Setting this to any other value will
		result in an error."
::= { in3000SelfTests 4 }

netioTest OBJECT-TYPE
	SYNTAX	INTEGER
	{
           testPass(1),
           testFailed(2),
           testHub1(3),
           testHub2(4),
           testHub3(5),
           testHub4(6)
	}
	ACCESS 	read-write
	STATUS	mandatory
	DESCRIPTION
		"This variable is used to run a diagnostic test on
		the ethernet modules in the microhubs.

		To run the test this variable must be set to
		testHub1, testHub2, testHub3 or testHub4. Setting this
		to any other value will result in an error."
::= { in3000SelfTests 5 }

heapTest OBJECT-TYPE
	SYNTAX	INTEGER
	{
           testPass(1),
           testFailed(2),
           runTest(3)
	}
	ACCESS 	read-write
	STATUS	mandatory
	DESCRIPTION
		"This variable is used to run a diagnostic test on
		the memory heap.

		To run the test this variable must be set to
		runTest(3). Setting this to any other value will
		result in an error."
::= { in3000SelfTests 6 }


-- Traps are defined using the conventions in RFC 1215 [8].

partState TRAP-TYPE
 ENTERPRISE  in3000
 VARIABLES{ psmGroupIndex,
	    psmPortIndex  }
 DESCRIPTION
	"This trap is sent whenever the partition state changes to partitioned."
 ::= 1

 notPartState TRAP-TYPE
 ENTERPRISE  in3000
 VARIABLES{ psmGroupIndex,
	    psmPortIndex  }
 DESCRIPTION
	"This trap is sent whenever the partition state changes to not partitioned."
 ::= 2

END
