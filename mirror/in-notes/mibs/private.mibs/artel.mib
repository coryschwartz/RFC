ARTEL-MIB DEFINITIONS ::= BEGIN



-- Title:	ARTEL MIB		@(#)artel.mib	1.7 7/21/93
-- Date:	May 29, 1992
-- Version 2 Update:	June 15, 1993


IMPORTS
	enterprises, IpAddress, Counter, Gauge, TimeTicks, Opaque
		FROM RFC1155-SMI
	OBJECT-TYPE
		FROM RFC-1212
	DisplayString, PhysAddress
		FROM RFC1213-MIB;

			  	
	artel             OBJECT IDENTIFIER ::= { enterprises 139 }

	node              OBJECT IDENTIFIER ::= { artel 1 }
	galactica         OBJECT IDENTIFIER ::= { artel 2 }
	artelTrap         OBJECT IDENTIFIER ::= { artel 64 }

	board             OBJECT IDENTIFIER ::= { galactica 1 }
	arcnet            OBJECT IDENTIFIER ::= { galactica 2 }
	backplane         OBJECT IDENTIFIER ::= { galactica 3 }
	bridge            OBJECT IDENTIFIER ::= { galactica 4 }
	systemManagement  OBJECT IDENTIFIER ::= { galactica 5 }
	starbridge        OBJECT IDENTIFIER ::= { galactica 6 }
	fddi              OBJECT IDENTIFIER ::= { galactica 7 }

	
	-- node group
	
	nodeName  OBJECT-TYPE
		SYNTAX  DisplayString (SIZE (0..255))
		ACCESS  read-write
		STATUS  mandatory
		DESCRIPTION
			"This node's administratively assigned name."
	::= { node 1 }

	nodeMacSlotMap  OBJECT-TYPE
		SYNTAX  Opaque
		ACCESS  read-only
		STATUS  mandatory
		DESCRIPTION
			"Each Starbridge board is assigned a base physical address.
			The physical address for each port is then assigned as
			(baseAddress + portIndex - 1).  The nodeMacSlotMap is a
			5 element array of the hex coded base addresses contained
			in the node with empty slots assigned the base address of
			00:00:00:00:00:00."
	::= { node 2 }



	nodeColdBoot  OBJECT-TYPE
		SYNTAX  INTEGER
		ACCESS  read-write
		STATUS  mandatory
		DESCRIPTION
			"When queried, this object will always return the value 1.
			Setting this object to any value causes the node to reset
			which has the effect of resetting all the boards in the node."
	::= { node 3 }
     
	nodeResetNvRam  OBJECT-TYPE
		SYNTAX  INTEGER
		ACCESS  read-write
		STATUS  mandatory
		DESCRIPTION
			"When queried, this object will always return the value 1.
			Setting this object to any value causes the node to reset
			the non-volatile RAM in each board in the node to default
			values."
	::= { node 4 }
     
	nodeIpSlotTable  OBJECT-TYPE
		SYNTAX  SEQUENCE OF NodeIpSlotEntry
		ACCESS  not-accessible
		STATUS  mandatory
		DESCRIPTION
			"A table that contains the IP addresses of the boards in the node."
	::= { node 5 }
     
	nodeIpSlotEntry  OBJECT-TYPE
		SYNTAX  NodeIpSlotEntry
		ACCESS  not-accessible
		STATUS  mandatory
		DESCRIPTION
			"The IP address of one of the boards in the node."
		INDEX  { nodeIpSlotIndex }
	::= { nodeIpSlotTable 1 }
     
	NodeIpSlotEntry ::=
		SEQUENCE {
			nodeIpSlotIndex
				INTEGER,
			nodeIpSlotAddr
				IpAddress
		}
     
	nodeIpSlotIndex  OBJECT-TYPE
		SYNTAX  INTEGER (1..9)
		ACCESS  read-only
		STATUS  mandatory
		DESCRIPTION
			"The slot number in the node."
	::= { nodeIpSlotEntry 1 }
     
	nodeIpSlotAddr  OBJECT-TYPE
		SYNTAX  IpAddress
		ACCESS  read-write
		STATUS  mandatory
		DESCRIPTION
			"The IP address of the board in slot nodeIpSlotIndex."
	::= { nodeIpSlotEntry 2 }
     


     -- board group

     
     boardIpAddr  OBJECT-TYPE
          SYNTAX  IpAddress
	  ACCESS  read-write
          STATUS  mandatory
          DESCRIPTION
	     "The administratively assigned IP Address for this board."
	  ::= { board 1 }



     boardReset  OBJECT-TYPE
        SYNTAX    INTEGER
	ACCESS    read-write
        STATUS    mandatory
        DESCRIPTION
	     "When queried, this object will always return the value 1.
             Setting this object to any value causes the board to reset."
	::= { board 3 }



     boardResetNvRam  OBJECT-TYPE
        SYNTAX    INTEGER
	ACCESS    read-write
        STATUS    mandatory
        DESCRIPTION
	   "When queried, this object will always return the value 1.
           Setting this object to any value causes the non-volatile
	   ram to be reset to their default values."
	::= { board 4 }



     boardLedStatus  OBJECT-TYPE
        SYNTAX  INTEGER
	ACCESS  read-only
        STATUS  mandatory
        DESCRIPTION
	   "The returns 16 bits encoded as an integer that represent
	   the LEDs found on the front panel of the System Management
	   board and on internal LED displays on the Starbridge Board.
	   The most significant bit represents the leftmost LED.

	   PLEASE NOTE:  If the bit is 1 it indicates that the LED is OFF.
	   If the bit is 0 it indicates that the LED is ON."
	::= { board 5 }


     boardSlotNum  OBJECT-TYPE
        SYNTAX  INTEGER
	ACCESS  read-only
        STATUS  mandatory
        DESCRIPTION
	   "The Galactica Chassis slot that this board resides in.  The
	   slots are numbered 0 thru n with 0 being the bottom slot."
	::= { board 6 }


	boardClass  OBJECT-TYPE
		SYNTAX  INTEGER {
			system-management-board(1),
			starbridge-board(2),
			turbo(3),
			fddi-board(4)
		}
		ACCESS  read-only
		STATUS  mandatory
		DESCRIPTION
			"The type of board/device."
	::= { board 7 }




     boardResetCounts  OBJECT-TYPE
        SYNTAX  Counter
	ACCESS  read-only
        STATUS  mandatory
        DESCRIPTION
	   "The number of times the 68K processor on this board has
	   reset since the last time the non-volatile ram has been
	   reset to default values." 
	::= { board 8 }




     boardSnmpMibVersion  OBJECT-TYPE
        SYNTAX  DisplayString (SIZE (0..255))
	ACCESS  read-only
        STATUS  mandatory
        DESCRIPTION
	   "The version of the Artel Proprietary MIB supported by this board."
	::= { board 9 }


     -- arcnet group

	
     arcnetBoardsPresent  OBJECT-TYPE
          SYNTAX  INTEGER
	  ACCESS  read-only
          STATUS  mandatory
          DESCRIPTION
	     "A 17 bit bit-significant register returned as an
	     integer.  If the bit is set there is a board in that
	     slot.  The least significant bit represents slot 0.  The
	     most significant bit represents the System Management board."
	  ::= { arcnet 1 }



     arcnetRxPkts  OBJECT-TYPE
          SYNTAX  Counter
	  ACCESS  read-only
          STATUS  mandatory
          DESCRIPTION
	     "The total number of packets received by this board over the
	     internal Arcnet interface."
	  ::= { arcnet 2 }



     arcnetTxPkts  OBJECT-TYPE
          SYNTAX  Counter
	  ACCESS  read-only
          STATUS  mandatory
          DESCRIPTION
	     "The total number of packets transmitted by this board
	     over the internal Arcnet interface."
	  ::= { arcnet 3 }



     arcnetNakCnts  OBJECT-TYPE
          SYNTAX  Counter
	  ACCESS  read-only
          STATUS  mandatory
          DESCRIPTION
	     "The number of Negative Acknowledgements received by
	     this board over the internal Arcnet interface when
	     attemting to transmit."
	  ::= { arcnet 4 }



     arcnetMyReconfigCounts  OBJECT-TYPE
          SYNTAX  Counter
	  ACCESS  read-only
          STATUS  mandatory
          DESCRIPTION
	     "The number of times the internal Arcnet bus has
	     been reconfigured by this board."
	  ::= { arcnet 5 }



     arcnetReconfigCounts  OBJECT-TYPE
          SYNTAX  Counter
	  ACCESS  read-only
          STATUS  mandatory
          DESCRIPTION
	     "The total number of times the internal Arcnet bus has
	     been reconfigured since powerup."
	  ::= { arcnet 6 }



     arcnetTrashedRxMsgs  OBJECT-TYPE
          SYNTAX  Counter
	  ACCESS  read-only
          STATUS  mandatory
          DESCRIPTION
	     "The number of Arcnet receive messages that were discarded by
	     this board."
	  ::= { arcnet 7 }



     arcnetTrashedTxMsgs  OBJECT-TYPE
          SYNTAX  Counter
	  ACCESS  read-only
          STATUS  mandatory
          DESCRIPTION
	     "The number of Arcnet transmit messages that were
	     discarded by this board."
	  ::= { arcnet 8 }

     
	--  backplane group

	bpStatsEnabled  OBJECT-TYPE
		SYNTAX  INTEGER {
			enabled(1),
			disabled(2)
		}
		ACCESS  read-write
		STATUS  mandatory
		DESCRIPTION
			"The administrative state of this boards connection to
			the Galactica 1 gigabit GBus."
	::= { backplane 1 }


	bpStatsRxPkts  OBJECT-TYPE
		SYNTAX  Counter
		ACCESS  read-only
		STATUS  mandatory
		DESCRIPTION
			"Total number of packets received by this board from the
			Galactica 1 gigabit GBus." 
	::= { backplane 2 }


	bpStatsRxErrors  OBJECT-TYPE
		SYNTAX  Counter
		ACCESS  read-only
		STATUS  mandatory
		DESCRIPTION
			"Number of received packets that were received from the
			Galactica 1 gigabit GBus that contained errors."
	::= { backplane 3 }


	bpStatsTxPkts  OBJECT-TYPE
		SYNTAX  Counter
		ACCESS  read-only
		STATUS  mandatory
		DESCRIPTION
			"Total number of packets transmitted by this board from
			the Galactica 1 gigabit GBus." 
	::= { backplane 4 }


	bpStatsTxErrors  OBJECT-TYPE
		SYNTAX  Counter
		ACCESS  read-only
		STATUS  mandatory
		DESCRIPTION
			"Number of packets which could not be transmitted because
			the receiver board was busy."
	::= { backplane 5 }


	bpStatsOperState  OBJECT-TYPE
		SYNTAX  INTEGER {
			enabled(1),
			disabled(2)
		}
		ACCESS  read-only
		STATUS  mandatory
		DESCRIPTION
			"Operational state of this boards connection to the
			Galactica 1 gigabit GBus." 
	::= { backplane 6 }
     
	bpStatsInitialize  OBJECT-TYPE
		SYNTAX  INTEGER
		ACCESS  read-write
		STATUS  mandatory
		DESCRIPTION
			"When queried, this object will always return the value 1.
			Setting this object to any value causes the Backplane statistics
			to be cleared."
	::= { backplane 7 }

	bpStatsTxQOverErrors  OBJECT-TYPE
		SYNTAX  Counter
		ACCESS  read-only
		STATUS  mandatory
		DESCRIPTION
			"A count of the number of overflows of the backplane transmit
			queue."
	::= { backplane 8 }
     
	bpStatsRxBusyTable  OBJECT-TYPE
		SYNTAX  SEQUENCE OF BpStatsRxBusyTableEntry
		ACCESS  not-accessible
		STATUS  mandatory
		DESCRIPTION
			"A table stored on each board (except System Managers) that
			counts the number of packets transmitted by this board across
			the backplane that had to be discarded because the receiving
			board was too busy."
	::= { backplane 9 }
     
	bpStatsRxBusyTableEntry  OBJECT-TYPE
		SYNTAX  BpStatsRxBusyTableEntry
		ACCESS  not-accessible
		STATUS  mandatory
		DESCRIPTION
			"An entry for another board in the node that counts the number
			of backplane packets from this board that the other board was
			too busy to receive."
		INDEX  { bpStatsRxBusyTableIndex }
	::= { bpStatsRxBusyTable 1 }
     
	BpStatsRxBusyTableEntry ::=
		SEQUENCE {
			bpStatsRxBusyTableIndex
				INTEGER,
			bpStatsRxBusyTableErrors
				Counter
		}
     
	bpStatsRxBusyTableIndex  OBJECT-TYPE
		SYNTAX  INTEGER (1..9)
		ACCESS  read-only
		STATUS  mandatory
		DESCRIPTION
			"The slot number of the receiving board."
	::= { bpStatsRxBusyTableEntry 1 }

	bpStatsRxBusyTableErrors  OBJECT-TYPE
		SYNTAX  Counter
		ACCESS  read-only
		STATUS  mandatory
		DESCRIPTION
			"A count of the number of backplane packets transmitted by this
			board to the board in slot bpStatsRxBusyTableIndex that the
			other board was too busy to receive."
	::= { bpStatsRxBusyTableEntry 2 }


	-- bridge group

	restrictedTable OBJECT-TYPE
		SYNTAX  SEQUENCE OF RestrictedEntry
		ACCESS  not-accessible
		STATUS  mandatory
		DESCRIPTION
			"A table of physical addresses that are restricted from
			being bridged through this node.  Filtering is done on
			both source and destination address."
	::= { bridge 1 }

	restrictedEntry OBJECT-TYPE
		SYNTAX  RestrictedEntry
		ACCESS  not-accessible
		STATUS  mandatory
		DESCRIPTION
			"Information needed to restrict a particular physical address."
		INDEX   { restrictedAddr }
	::= { restrictedTable 1 }

	RestrictedEntry ::=
		SEQUENCE {
			restrictedAddr
				PhysAddress,
			restrictedStatus
				INTEGER
		}

	restrictedAddr  OBJECT-TYPE
		SYNTAX  PhysAddress (SIZE (0..6))
		ACCESS  read-write
		STATUS  mandatory
		DESCRIPTION
			"The physical address to be restricted."
	::= { restrictedEntry 1 }

	restrictedStatus  OBJECT-TYPE
		SYNTAX  INTEGER {
			valid(1),
			invalid(2)
		}
		ACCESS  read-write
		STATUS  mandatory
		DESCRIPTION
			"Indicates the state of the entry.  Invalid items will
			be removed from the table."
	::= { restrictedEntry 2 }


     bridgeAgeNow  OBJECT-TYPE
          SYNTAX  INTEGER
	  ACCESS  read-write
          STATUS  mandatory
          DESCRIPTION
	     "When queried, this object will always return the value 1.
             Setting this object to any value causes the forwarding
	     database to be fully aged."
	  ::= { bridge 2 }


     bridgeDot1dEnable  OBJECT-TYPE
          SYNTAX  INTEGER {
		     enabled(1),
		     disabled(2)
		  }
	  ACCESS  read-write
          STATUS  mandatory
          DESCRIPTION
	     "Enables and disables the IEE 802.1d Spanning Tree
	     Protocol for the board."
	  ::= { bridge 3 }


     bridgeDot1dResetDefaults  OBJECT-TYPE
          SYNTAX  INTEGER
	  ACCESS  read-write
          STATUS  mandatory
          DESCRIPTION
	     "When queried, this object will always return the value 1.
             Setting this object to any value causes the Spanning
	     Tree objects to be reset to the default values."
	  ::= { bridge 4 }


     bridgeResetPktSwCount  OBJECT-TYPE
          SYNTAX  INTEGER
	  ACCESS  read-only
          STATUS  mandatory
          DESCRIPTION
             "A count of the number of times the packet switching
	     function has been reset." 
	  ::= { bridge 6 }



     bridgePktSwLastReset  OBJECT-TYPE
          SYNTAX  TimeTicks
	  ACCESS  read-only
          STATUS  mandatory
          DESCRIPTION
             "The value of sysUpTime when the packet swtiching
	     function was last reset." 
	  ::= { bridge 7 }

	  

     bridgeResetStatic  OBJECT-TYPE
          SYNTAX  INTEGER
	  ACCESS  read-write
          STATUS  mandatory
          DESCRIPTION
	     "When queried, this object will always return the value 1.
             Setting this object to any value causes the static table
	     to be cleared."
	  ::= { bridge 8 }

	  
     bridgeRestrictedReset  OBJECT-TYPE
          SYNTAX  INTEGER
	  ACCESS  read-write
          STATUS  mandatory
          DESCRIPTION
	     "When queried, this object will always return the value 1.
             Setting this object to any value causes the restricted
	     table to be cleared."
	  ::= { bridge 9 }

     
	-- User Defined Filters section
     
	bridgeUdfTable  OBJECT-TYPE
		SYNTAX  SEQUENCE OF BridgeUdfEntry
		ACCESS  not-accessible
		STATUS  mandatory
		DESCRIPTION
			"A table maintaining user defined filtering information on
			each port on the board."
	::= { bridge 11 }
     
	bridgeUdfEntry OBJECT-TYPE
		SYNTAX  BridgeUdfEntry
		ACCESS  not-accessible
		STATUS  mandatory
		DESCRIPTION
			"User defined filtering information maintained on a single port
			and filter."
		INDEX  { bridgeUdfPortIndex, bridgeUdfFilterIndex }
	::= { bridgeUdfTable 1 }
     
	BridgeUdfEntry ::=
		SEQUENCE {
			bridgeUdfPortIndex
				INTEGER,
			bridgeUdfFilterIndex
				INTEGER,
			bridgeUdfState
				INTEGER,
			bridgeUdfComment
				DisplayString,
			bridgeUdfMatchCounts
				Counter,
			bridgeUdfInitMatchCount
				INTEGER,
			bridgeUdfAddressType
				INTEGER,
			bridgeUdfAddressValue
				PhysAddress,
			bridgeUdfAddressMask
				PhysAddress,
			bridgeUdfAddressOperand
				INTEGER,
			bridgeUdfTypeValue
				INTEGER,
			bridgeUdfTypeMask
				INTEGER,
			bridgeUdfTypeOperand
				INTEGER,
			bridgeUdfOffset1Offset
				INTEGER,
			bridgeUdfOffset1Value
				INTEGER,
			bridgeUdfOffset1Mask
				INTEGER,
			bridgeUdfOffset1Operand
				INTEGER,
			bridgeUdfOffset2Offset
				INTEGER,
			bridgeUdfOffset2Value
				INTEGER,
			bridgeUdfOffset2Mask
				INTEGER,
			bridgeUdfOffset2Operand
				INTEGER,
			bridgeUdfOffset3Offset
				INTEGER,
			bridgeUdfOffset3Value
				INTEGER,
			bridgeUdfOffset3Mask
				INTEGER,
			bridgeUdfOffset3Operand
				INTEGER,
			bridgeUdfOffset4Offset
				INTEGER,
			bridgeUdfOffset4Value
				INTEGER,
			bridgeUdfOffset4Mask
				INTEGER,
			bridgeUdfOffset4Operand
				INTEGER
		}
     
	bridgeUdfPortIndex  OBJECT-TYPE
		SYNTAX  INTEGER (1..8)
		ACCESS  read-only
		STATUS  mandatory
		DESCRIPTION
			"The port number on the board. Same as ifIndex."
	::= { bridgeUdfEntry 1 }

	bridgeUdfFilterIndex  OBJECT-TYPE
		SYNTAX  INTEGER (1..8)
		ACCESS  read-only
		STATUS  mandatory
		DESCRIPTION
			"The filter number for the port."
	::= { bridgeUdfEntry 2 }

	bridgeUdfState  OBJECT-TYPE
		SYNTAX  INTEGER  {
			disabled(1),
			filter(2),
			forward(3),
			count(4)
		}
		ACCESS  read-write
		STATUS  mandatory
		DESCRIPTION
			"The state of this filter. There are four states: disabled,
			filter, forward and count. In the disabled state, this filter
			is ignored. In the filter state, a packet matching this filter
			will be filtered or discarded. In the forward state, a packet
			matching this filter will be forwarded. In the count state, a
			packet matching this filter will increment the bridgeUdfMatchCounts
			and the filter will be ignored for filtering and forwarding
			purposes."
	::= { bridgeUdfEntry 3 }

	bridgeUdfComment  OBJECT-TYPE
		SYNTAX  DisplayString (SIZE (0..255))
		ACCESS  read-write
		STATUS  mandatory
		DESCRIPTION
			"A comment field to describe this filter."
	::= { bridgeUdfEntry 4 }

	bridgeUdfMatchCounts  OBJECT-TYPE
		SYNTAX  Counter
		ACCESS  read-only
		STATUS  mandatory
		DESCRIPTION
			"The number of packets that matched this filter when the
			bridgeUdfState was either filter, forward or count."
	::= { bridgeUdfEntry 5 }
     
	bridgeUdfInitMatchCount  OBJECT-TYPE
		SYNTAX  INTEGER
		ACCESS  read-write
		STATUS  mandatory
		DESCRIPTION
			"When read this object always returns 1. When set to any value
			it will clear the bridgeUdfMatchCounts object for this port
			and filter."
	::= { bridgeUdfEntry 6 }

	bridgeUdfAddressType  OBJECT-TYPE
		SYNTAX  INTEGER  {
			source(1),
			destination(2)
		}
		ACCESS  read-write
		STATUS  mandatory
		DESCRIPTION
			"Source indicates that the address portion of this filter is
			using the source MAC address. Destination indicates the address
			portion of this filter is using the destination MAC address."
	::= { bridgeUdfEntry 7 }

	bridgeUdfAddressValue  OBJECT-TYPE
		SYNTAX  PhysAddress
		ACCESS  read-write
		STATUS  mandatory
		DESCRIPTION
			"The data value used for comparison on the MAC address in the
			packet."
	::= { bridgeUdfEntry 8 }

	bridgeUdfAddressMask  OBJECT-TYPE
		SYNTAX  PhysAddress
		ACCESS  read-write
		STATUS  mandatory
		DESCRIPTION
			"The value used to mask off the data value used for comparison
			on the MAC address in the packet. Don't care bits are zero."
	::= { bridgeUdfEntry 9 }
	
	bridgeUdfAddressOperand  OBJECT-TYPE
		SYNTAX  INTEGER  {
			equal(1),
			notequal(2),
			lessthan(3),
			lessthanorequal(4),
			greaterthan(5),
			greaterthanorequal(6)
		}
		ACCESS  read-write
		STATUS  mandatory
		DESCRIPTION
			"The operand used in the comparison of the bridgeUdfAddressValue
			and the MAC address in the packet."
	::= { bridgeUdfEntry 10 }

	bridgeUdfTypeValue  OBJECT-TYPE
		SYNTAX  INTEGER
		ACCESS  read-write
		STATUS  mandatory
		DESCRIPTION
			"The data value used for comparison on the type field in the
			packet."
	::= { bridgeUdfEntry 11 }

	bridgeUdfTypeMask  OBJECT-TYPE
		SYNTAX  INTEGER
		ACCESS  read-write
		STATUS  mandatory
		DESCRIPTION
			"The value used to mask off the data value used for comparison
			on the type field in the packet. Don't care bits are zero."
	::= { bridgeUdfEntry 12 }

	bridgeUdfTypeOperand  OBJECT-TYPE
		SYNTAX  INTEGER  {
			equal(1),
			notequal(2),
			lessthan(3),
			lessthanorequal(4),
			greaterthan(5),
			greaterthanorequal(6)
		}
		ACCESS  read-write
		STATUS  mandatory
		DESCRIPTION
			"The operand used in the comparison of the bridgeUdfTypeValue
			and the type field in the packet."
	::= { bridgeUdfEntry 13 }

	bridgeUdfOffset1Offset  OBJECT-TYPE
		SYNTAX  INTEGER
		ACCESS  read-write
		STATUS  mandatory
		DESCRIPTION
			"The number of bytes from the start of the MAC header to the
			start of the data area in the packet to be used in the filter's
			comparison. This value must be divisible by 4."
	::= { bridgeUdfEntry 14 }

	bridgeUdfOffset1Value  OBJECT-TYPE
		SYNTAX  INTEGER
		ACCESS  read-write
		STATUS  mandatory
		DESCRIPTION
			"The data value used for comparison on the offset1 field as
			specified by bridgeUdfOffset1Offset in the packet."
	::= { bridgeUdfEntry 15 }

	bridgeUdfOffset1Mask  OBJECT-TYPE
		SYNTAX  INTEGER
		ACCESS  read-write
		STATUS  mandatory
		DESCRIPTION
			"The value used to mask off the data value used for comparison
			on the offset1 field in the packet. Don't care bits are zero."
	::= { bridgeUdfEntry 16 }

	bridgeUdfOffset1Operand  OBJECT-TYPE
		SYNTAX  INTEGER  {
			equal(1),
			notequal(2),
			lessthan(3),
			lessthanorequal(4),
			greaterthan(5),
			greaterthanorequal(6)
		}
		ACCESS  read-write
		STATUS  mandatory
		DESCRIPTION
			"The operand used in the comparison of the bridgeUdfOffset1Value
			and the type field in the packet."
	::= { bridgeUdfEntry 17 }

	bridgeUdfOffset2Offset  OBJECT-TYPE
		SYNTAX  INTEGER
		ACCESS  read-write
		STATUS  mandatory
		DESCRIPTION
			"The number of bytes from the start of the MAC header to the
			start of the data area in the packet to be used in the filter's
			comparison. This value must be divisible by 4."
	::= { bridgeUdfEntry 18 }

	bridgeUdfOffset2Value  OBJECT-TYPE
		SYNTAX  INTEGER
		ACCESS  read-write
		STATUS  mandatory
		DESCRIPTION
			"The data value used for comparison on the offset1 field as
			specified by bridgeUdfOffset2Offset in the packet."
	::= { bridgeUdfEntry 19 }

	bridgeUdfOffset2Mask  OBJECT-TYPE
		SYNTAX  INTEGER
		ACCESS  read-write
		STATUS  mandatory
		DESCRIPTION
			"The value used to mask off the data value used for comparison
			on the offset2 field in the packet. Don't care bits are zero."
	::= { bridgeUdfEntry 20 }

	bridgeUdfOffset2Operand  OBJECT-TYPE
		SYNTAX  INTEGER  {
			equal(1),
			notequal(2),
			lessthan(3),
			lessthanorequal(4),
			greaterthan(5),
			greaterthanorequal(6)
		}
		ACCESS  read-write
		STATUS  mandatory
		DESCRIPTION
			"The operand used in the comparison of the bridgeUdfOffset2Value
			and the type field in the packet."
	::= { bridgeUdfEntry 21 }

	bridgeUdfOffset3Offset  OBJECT-TYPE
		SYNTAX  INTEGER
		ACCESS  read-write
		STATUS  mandatory
		DESCRIPTION
			"The number of bytes from the start of the MAC header to the
			start of the data area in the packet to be used in the filter's
			comparison. This value must be divisible by 4."
	::= { bridgeUdfEntry 22 }

	bridgeUdfOffset3Value  OBJECT-TYPE
		SYNTAX  INTEGER
		ACCESS  read-write
		STATUS  mandatory
		DESCRIPTION
			"The data value used for comparison on the offset1 field as
			specified by bridgeUdfOffset3Offset in the packet."
	::= { bridgeUdfEntry 23 }

	bridgeUdfOffset3Mask  OBJECT-TYPE
		SYNTAX  INTEGER
		ACCESS  read-write
		STATUS  mandatory
		DESCRIPTION
			"The value used to mask off the data value used for comparison
			on the offset3 field in the packet. Don't care bits are zero."
	::= { bridgeUdfEntry 24 }

	bridgeUdfOffset3Operand  OBJECT-TYPE
		SYNTAX  INTEGER  {
			equal(1),
			notequal(2),
			lessthan(3),
			lessthanorequal(4),
			greaterthan(5),
			greaterthanorequal(6)
		}
		ACCESS  read-write
		STATUS  mandatory
		DESCRIPTION
			"The operand used in the comparison of the bridgeUdfOffset3Value
			and the type field in the packet."
	::= { bridgeUdfEntry 25 }

	bridgeUdfOffset4Offset  OBJECT-TYPE
		SYNTAX  INTEGER
		ACCESS  read-write
		STATUS  mandatory
		DESCRIPTION
			"The number of bytes from the start of the MAC header to the
			start of the data area in the packet to be used in the filter's
			comparison. This value must be divisible by 4."
	::= { bridgeUdfEntry 26 }

	bridgeUdfOffset4Value  OBJECT-TYPE
		SYNTAX  INTEGER
		ACCESS  read-write
		STATUS  mandatory
		DESCRIPTION
			"The data value used for comparison on the offset1 field as
			specified by bridgeUdfOffset4Offset in the packet."
	::= { bridgeUdfEntry 27 }

	bridgeUdfOffset4Mask  OBJECT-TYPE
		SYNTAX  INTEGER
		ACCESS  read-write
		STATUS  mandatory
		DESCRIPTION
			"The value used to mask off the data value used for comparison
			on the offset4 field in the packet. Don't care bits are zero."
	::= { bridgeUdfEntry 28 }

	bridgeUdfOffset4Operand  OBJECT-TYPE
		SYNTAX  INTEGER  {
			equal(1),
			notequal(2),
			lessthan(3),
			lessthanorequal(4),
			greaterthan(5),
			greaterthanorequal(6)
		}
		ACCESS  read-write
		STATUS  mandatory
		DESCRIPTION
			"The operand used in the comparison of the bridgeUdfOffset4Value
			and the type field in the packet."
	::= { bridgeUdfEntry 29 }

	bridgeUdfInitCountTable  OBJECT-TYPE
		SYNTAX  SEQUENCE OF BridgeUdfInitCountEntry
		ACCESS  not-accessible
		STATUS  mandatory
		DESCRIPTION
			"A table used to clear all of a port's bridgeUdfMatchCounts."
	::= { bridge 12 }
     
	bridgeUdfInitCountEntry  OBJECT-TYPE
		SYNTAX  BridgeUdfInitCountEntry
		ACCESS  not-accessible
		STATUS  mandatory
		DESCRIPTION
			"A table entry used to clear all of a port's bridgeUdfMatchCounts."
		INDEX  { bridgeUdfCountPortIndex }
	::= { bridgeUdfInitCountTable 1 }
     
	BridgeUdfInitCountEntry ::=
		SEQUENCE {
			bridgeUdfCountPortIndex
				INTEGER,
			bridgeUdfCountInitMatchCount
				INTEGER
		}
     
	bridgeUdfCountPortIndex  OBJECT-TYPE
		SYNTAX  INTEGER (1..8)
		ACCESS  read-only
		STATUS  mandatory
		DESCRIPTION
			"The port number on the board. Same as ifIndex."
	::= { bridgeUdfInitCountEntry 1 }
     
	bridgeUdfCountInitMatchCount  OBJECT-TYPE
		SYNTAX  INTEGER
		ACCESS  read-write
		STATUS  mandatory
		DESCRIPTION
			"When read this object always returns 1. When set to any value
			it will clear all of the bridgeUdfMatchCounts objects for this
			port."
	::= { bridgeUdfInitCountEntry 2 }
     
     
	-- Port Groups

	bridgePortGroupEnable  OBJECT-TYPE
		SYNTAX  INTEGER {
			enabled(1),
			disabled(2)
		}
		ACCESS  read-write
		STATUS  mandatory
		DESCRIPTION
			"Enables and disables all Port Group filtering for the node."
	::= { bridge 13 }
     
	bridgePortGroupTable  OBJECT-TYPE
		SYNTAX  SEQUENCE OF BridgePortGroupEntry
		ACCESS  not-accessible
		STATUS  mandatory
		DESCRIPTION
			"A table containing the port group information on each port and
			group in the node."
	::= { bridge 14 }
     
	bridgePortGroupEntry  OBJECT-TYPE
		SYNTAX  BridgePortGroupEntry
		ACCESS  not-accessible
		STATUS  mandatory
		DESCRIPTION
			"Port group information maintained on a single port and group."
		INDEX  { bridgePortGroupTablePortIndex, bridgePortGroupTableGroupIndex }
	::= { bridgePortGroupTable 1 }
     
	BridgePortGroupEntry ::=
		SEQUENCE {
			bridgePortGroupTablePortIndex
				INTEGER,
			bridgePortGroupTableGroupIndex
				INTEGER,
			bridgePortGroupTableEnable
				INTEGER
		}
     
	bridgePortGroupTablePortIndex  OBJECT-TYPE
		SYNTAX  INTEGER (1..40)
		ACCESS  read-only
		STATUS  mandatory
		DESCRIPTION
			"The port number in the node."
	::= { bridgePortGroupEntry 1 }
     
	bridgePortGroupTableGroupIndex  OBJECT-TYPE
		SYNTAX  INTEGER (1..16)
		ACCESS  read-only
		STATUS  mandatory
		DESCRIPTION
			"The group number in the node."
	::= { bridgePortGroupEntry 2 }
     
	bridgePortGroupTableEnable  OBJECT-TYPE
		SYNTAX  INTEGER {
			enable(1),
			disable(2)
		}
		ACCESS  read-write
		STATUS  mandatory
		DESCRIPTION
			"This object indicates the status of this entry.
			enable(1) - This port is currently contained in this group.
			disable(2) - This port is not currently contained in this group."
	::= { bridgePortGroupEntry 3 }
     
	bridgePortGroupPortTable  OBJECT-TYPE
		SYNTAX  SEQUENCE OF BridgePortGroupPortEntry
		ACCESS  not-accessible
		STATUS  mandatory
		DESCRIPTION
			"A table containing the port group information as readable strings
			on each port on the board."
	::= { bridge 15 }
     
	bridgePortGroupPortEntry  OBJECT-TYPE
		SYNTAX  BridgePortGroupPortEntry
		ACCESS  not-accessible
		STATUS  mandatory
		DESCRIPTION
			"Port group information maintained on a single port."
		INDEX  { bridgePortGroupPortIndex }
	::= { bridgePortGroupPortTable 1 }
     
	BridgePortGroupPortEntry ::=
		SEQUENCE {
			bridgePortGroupPortIndex
				INTEGER,
			bridgePortGroupPortDisplayString
				DisplayString
		}
     
	bridgePortGroupPortIndex  OBJECT-TYPE
		SYNTAX  INTEGER (1..8)
		ACCESS  read-only
		STATUS  mandatory
		DESCRIPTION
			"The port number on the board. Same as ifIndex."
	::= { bridgePortGroupPortEntry 1 }

	bridgePortGroupPortDisplayString  OBJECT-TYPE
		SYNTAX  DisplayString (SIZE (0..255))
		ACCESS  read-only
		STATUS  mandatory
		DESCRIPTION
			"A readable string that contains all of the port groups that
			this port is a member of."
	::= { bridgePortGroupPortEntry 2 }

	bridgePortGroupGroupTable  OBJECT-TYPE
		SYNTAX  SEQUENCE OF BridgePortGroupGroupEntry
		ACCESS  not-accessible
		STATUS  mandatory
		DESCRIPTION
			"A table maintaining the port group information for each group
			on the node."
	::= { bridge 16 }
     
	bridgePortGroupGroupEntry  OBJECT-TYPE
		SYNTAX  BridgePortGroupGroupEntry
		ACCESS  not-accessible
		STATUS  mandatory
		DESCRIPTION
			"Port group information maintained on a single port group."
		INDEX  { bridgePortGroupGroupIndex }
	::= { bridgePortGroupGroupTable 1 }
     
	BridgePortGroupGroupEntry ::=
		SEQUENCE {
			bridgePortGroupGroupIndex
				INTEGER,
			bridgePortGroupGroupPortMap
				OCTET STRING,
			bridgePortGroupGroupComment
				DisplayString
		}
     
	bridgePortGroupGroupIndex  OBJECT-TYPE
		SYNTAX  INTEGER (1..16)
		ACCESS  read-only
		STATUS  mandatory
		DESCRIPTION
			"The group number on the node."
	::= { bridgePortGroupGroupEntry 1 }

	bridgePortGroupGroupPortMap  OBJECT-TYPE
		SYNTAX  OCTET STRING
		ACCESS  read-write
		STATUS  mandatory
		DESCRIPTION
			"The set of ports which are members of this group. Packets can
			only be forwarded to ports in the same port group(s) as the port
			on which the packet was received. A port can be in multiple port
			groups. Each octet within the value of this object specifies a set
			of eight ports, with the first octet specifying ports 1 through
			8 on board 1, the second octet specifying ports 1 through 8 on
			board 2, etc. Within each octet the most significant bit represents
			the lowest numbered port, and the least significant bit represents
			the highest numbered port. Thus, each port of the bridge is
			represented by a single bit within the value of this object. If
			that bit has a value of '1' then that port is included in the set
			of ports; the port is not included if its bit has a value of '0'."
	::= { bridgePortGroupGroupEntry 2 }

	bridgePortGroupGroupComment  OBJECT-TYPE
		SYNTAX  DisplayString (SIZE (0..255))
		ACCESS  read-only
		STATUS  mandatory
		DESCRIPTION
			"A readable string that contains all of the port groups that
			this port is a member of."
	::= { bridgePortGroupGroupEntry 3 }
     
     
	-- Address Filtering Database
     
	bridgeAddrFilterTable  OBJECT-TYPE
		SYNTAX  SEQUENCE OF BridgeAddrFilterEntry
		ACCESS  not-accessible
		STATUS  mandatory
		DESCRIPTION
			"A table that contains information about MAC addresses for
			which the node has forwarding and/or filtering information.
			This information is used by the transparent bridging function
			in determining how to propagate a received frame."
	::= { bridge 17 }
     
	bridgeAddrFilterEntry  OBJECT-TYPE
		SYNTAX  BridgeAddrFilterEntry
		ACCESS  not-accessible
		STATUS  mandatory
		DESCRIPTION
			"Address filtering information maintained on a block of 100
			entries in the node's filtering database."
		INDEX  { bridgeAddrFilterBlockIndex }
	::= { bridgeAddrFilterTable 1 }
     
	BridgeAddrFilterEntry ::=
		SEQUENCE {
			bridgeAddrFilterBlockIndex
				INTEGER,
			bridgeAddrFilterBlockData
				Opaque
		}
     
	bridgeAddrFilterBlockIndex  OBJECT-TYPE
		SYNTAX  INTEGER (1..205)
		ACCESS  read-only
		STATUS  mandatory
		DESCRIPTION
			"Block number for this entry. Each block holds information on 100
			entry locations into the node's address filtering database."
	::= { bridgeAddrFilterEntry 1 }

	bridgeAddrFilterBlockData  OBJECT-TYPE
		SYNTAX  Opaque
		ACCESS  read-only
		STATUS  mandatory
		DESCRIPTION
			"There will be 100 address entries returned. Each address entry
			contains the following data:
			ENTRY NUMBER: 2 octets - The physical entry into the node's
			                         address filtering database for this
			                         address.
			MAC ADDRESS:  6 octets - The MAC address for this entry.
			ENTRY TYPE:   1 octet  - The type of entry can be one of the
			                         following:
			                            invalid(1)  : this entry is not valid.
			                            learned(2)  : the value of the PORT
                                                      and SLOT was learned,
                                                      and is being used.
                                        static(3)   : the address is in the
                                                      dot1dStaticTable with
                                                      the instance of the
                                                      MAC address.
                                        restrict(4) : the address is in the
                                                      restrictedTable with
                                                      the instance of the
                                                      MAC address.
                                        spantree(5) : the address is the
                                                      spanning tree group
                                                      address.
                                        self(6)     : The address is one of
                                                      the bridge's addresses.
                                                      The SLOT indicates which
                                                      of the node's boards has
                                                      this address.
			SLOT:        1 octet  - If 'learned' the slot number of the board
                                     on which a frame having a source address
                                     equal to the value of the MAC address has
                                     been seen. If 'self' the slot number of
                                     the board with that MAC address. Else
                                     a value of '0' indicating that the bridge
                                     does have some forwarding/filtering
                                     information about this MAC address (e.g.
                                     in the dot1dStaticTable).
			PORT:        1 octet  - If 'learned' the port number of the port
                                     on which a frame having a source address
                                     equal to the value of the MAC address has
                                     been seen. Else a value of '0' indicating
                                     that the bridge does have some forwarding/
                                     filtering information about this MAC
                                     address (e.g. in the dot1dStaticTable).
			AGE:         1 octet  - If 'learned' the value of the AGE flag:
                                       invalid(1)  : not valid for this entry.
                                       notaged(2)  : the MAC address has not
                                                     been aged.
                                       onceaged(3) : The MAC address has been
                                                     aged once. It will be
                                                     removed from the database
                                                     the next time the aging
                                                     process executes unless
                                                     a packet with the MAC
                                                     address in the source
                                                     address field is received."
	::= { bridgeAddrFilterEntry 2 }
     
	bridgedot1dTpFdbTable  OBJECT-TYPE
		SYNTAX  SEQUENCE OF Bridgedot1dTpFdbEntry
		ACCESS  not-accessible
		STATUS  mandatory
		DESCRIPTION
			"A table that contains information about MAC addresses for which
			the bridge has forwarding and/or filtering information. This
			information is used by the transparent bridging function in
			determining how to propagate a received frame. This table is an
			extension of the dot1dTpFdbTable."
	::= { bridge 18 }
     
     bridgedot1dTpFdbEntry  OBJECT-TYPE
          SYNTAX  Bridgedot1dTpFdbEntry
          ACCESS  not-accessible
          STATUS  mandatory
          DESCRIPTION
          "Information about a specific MAC address for which the bridge
          has some forwarding and/or filtering information."
          INDEX  { bridgedot1dTpFdbAddress }
     ::= { bridgedot1dTpFdbTable 1 }
     
     Bridgedot1dTpFdbEntry ::=
          SEQUENCE {
               bridgedot1dTpFdbAddress
                    PhysAddress,
               bridgedot1dTpFdbSlot
                    INTEGER,
               bridgedot1dTpFdbPort
                    INTEGER,
               bridgedot1dTpFdbStatus
                    INTEGER,
               bridgedot1dTpFdbAge
                    INTEGER
          }
     
     bridgedot1dTpFdbAddress  OBJECT-TYPE
          SYNTAX  PhysAddress (SIZE (6))
          ACCESS  read-only
          STATUS  mandatory
          DESCRIPTION
          "A MAC address for which the bridge has some forwarding and/or
          filtering information. Same as dot1dTpFdbAddress."
     ::= { bridgedot1dTpFdbEntry 1 }

     bridgedot1dTpFdbSlot  OBJECT-TYPE
          SYNTAX  INTEGER
          ACCESS  read-only
          STATUS  mandatory
          DESCRIPTION
          "If bridgeDot1dTpFdbStatus is 'learned' then the slot number of the
          board on which a frame having a source address equal to the value
          of the MAC address has been seen. If 'self' the slot number of the
          board with that MAC address. Else a value of '0' indicating that
          the bridge does have some forwarding/filtering information about
          this MAC address (e.g. in the dot1dStaticTable)."
     ::= { bridgedot1dTpFdbEntry 2 }

     bridgedot1dTpFdbPort  OBJECT-TYPE
          SYNTAX  INTEGER
          ACCESS  read-only
          STATUS  mandatory
          DESCRIPTION
          "If bridgeDot1dTpFdbStatus is 'learned' then the port number of the
          port on which a frame having a source address equal to the value
          of the MAC address has been seen. Else a value of '0' indicating that
          the bridge does have some forwarding/filtering information about
          this MAC address (e.g. in the dot1dStaticTable)."
     ::= { bridgedot1dTpFdbEntry 3 }

     bridgedot1dTpFdbStatus  OBJECT-TYPE
          SYNTAX  INTEGER {
               invalid(1),
               learned(2),
               static(3),
               restrict(4),
               spantree(5),
               self(6)
          }
          ACCESS  read-only
          STATUS  mandatory
          DESCRIPTION
          "The type of entry can be one of the following:
               invalid(1)  : This entry is not valid.
               learned(2)  : The value of the PORT and SLOT was learned,
                             and is being used.
               static(3)   : The address is in the dot1dStaticTable with
                             the instance of the MAC address.
               restrict(4) : The address is in the restrictedTable with
                             the instance of the MAC address.
               spantree(5) : The address is the spanning tree group address.
               self(6)     : The address is one of the bridge's addresses.
                             The port indicates which of the node's boards
                             has this address."
     ::= { bridgedot1dTpFdbEntry 4 }

     bridgedot1dTpFdbAge  OBJECT-TYPE
          SYNTAX  INTEGER {
               invalid(1),
               notaged(2),
               onceaged(3)
          }
          ACCESS  read-only
          STATUS  mandatory
          DESCRIPTION
          "If the bridgedot1dTpFdbStatus is 'learned' then the value of the
          AGE flag is:
               invalid(1)  : Not valid for this entry.
               notaged(2)  : The MAC address has not been aged.
               onceaged(3) : The MAC address has been aged once. It will be
                             removed from the database the next time the
                             aging process executes unless a packet with
                             the MAC address in the source address field
                             is received."
     ::= { bridgedot1dTpFdbEntry 5 }




     -- the following are all under the system management subtree
	  
     -- systemManagement.config group

     smConfiguration   OBJECT IDENTIFIER ::= { systemManagement 1 }
     
     
     smCfgManufactureDate  OBJECT-TYPE
          SYNTAX  DisplayString (SIZE (0..255))
	  ACCESS  read-only
          STATUS  mandatory
          DESCRIPTION
	     "The manufacture date of this System Management board."
	  ::= { smConfiguration 1 }




     smCfgType  OBJECT-TYPE
          SYNTAX  INTEGER {
	             system-management-board(1)
		  }
	  ACCESS  read-only
          STATUS  mandatory
          DESCRIPTION
	     "The type of board."
	  ::= { smConfiguration 2 }



     smCfgHardwareRev  OBJECT-TYPE
          SYNTAX  DisplayString (SIZE (0..255))
	  ACCESS  read-only
          STATUS  mandatory
          DESCRIPTION
	     "The hardware revision number of this System Management board."
	  ::= { smConfiguration 3 }



     smCfgSerialNumber  OBJECT-TYPE
          SYNTAX  DisplayString (SIZE (0..255))
	  ACCESS  read-only
          STATUS  mandatory
          DESCRIPTION
	     "The serial number of this System Management board."
	  ::= { smConfiguration 4 }



     smCfgMacAddr  OBJECT-TYPE
          SYNTAX  PhysAddress
	  ACCESS  read-only
          STATUS  mandatory
          DESCRIPTION
	     "The physical address of this System Management board."     
	  ::= { smConfiguration 5 }



     smCfgFlashMemSize  OBJECT-TYPE
          SYNTAX  INTEGER
	  ACCESS  read-only
          STATUS  mandatory
          DESCRIPTION
	     "Number of bytes of flash memory on this System
	     Management board."  
	  ::= { smConfiguration 6 }



     smCfg68kRamSize  OBJECT-TYPE
          SYNTAX  INTEGER
	  ACCESS  read-only
          STATUS  mandatory
          DESCRIPTION
	     "Management software RAM size on this System Management board."
	  ::= { smConfiguration 7 }



     smCfgBootRev  OBJECT-TYPE
          SYNTAX  DisplayString (SIZE (0..255))
	  ACCESS  read-only
          STATUS  mandatory
          DESCRIPTION
	     "Revision number and date of the boot software on this
	     System Management board." 
	  ::= { smConfiguration 8 }



     smCfg68kRev  OBJECT-TYPE
          SYNTAX  DisplayString (SIZE (0..255))
	  ACCESS  read-only
          STATUS  mandatory
          DESCRIPTION
	     "Revision number and date of the management software on
	     this System Management board."
	  ::= { smConfiguration 9 }



     smCfgModulePartNumber  OBJECT-TYPE
          SYNTAX  DisplayString (SIZE (0..255))
	  ACCESS  read-only
          STATUS  mandatory
          DESCRIPTION
	     "The Artel part number for this System Management module."
     	  ::= { smConfiguration 10 }



     smCfgModuleSerialNumber  OBJECT-TYPE
          SYNTAX  DisplayString (SIZE (0..255))
	  ACCESS  read-only
          STATUS  mandatory
          DESCRIPTION
	     "The Artel serial number for this System Management module."
	  ::= { smConfiguration 11 }


	
     smCfgStoreFlashRev  OBJECT-TYPE
          SYNTAX  DisplayString (SIZE (0..255))
	  ACCESS  read-only
          STATUS  mandatory
          DESCRIPTION
	     "The version number of the software loaded in the store flash
	     memory bank on this System Management board."
	  ::= { smConfiguration 12 }

	

     smCfgExecFlashRev  OBJECT-TYPE
          SYNTAX  DisplayString (SIZE (0..255))
	  ACCESS  read-only
          STATUS  mandatory
          DESCRIPTION
	     "The version number of the software loaded in the
	     executable flash memory bank on this System Management board."
	  ::= { smConfiguration 13 }


	  
     -- systemManagement.backplane group

     smBackplane   OBJECT IDENTIFIER ::= { systemManagement 2 }



     smBpType  OBJECT-TYPE
          SYNTAX  INTEGER {
		     five-Slot(5)
		  }
	       
	  ACCESS  read-only
          STATUS  mandatory
          DESCRIPTION
	     "The type of Galactica 1 gigabit GBus on this node."
	  ::= { smBackplane 1 }



     smBpArbTimer  OBJECT-TYPE
          SYNTAX  INTEGER
	  ACCESS  read-only
          STATUS  mandatory
          DESCRIPTION
	     "The timeout period used to switch from asyncronous
	     packets to syncronous packets."
	  ::= { smBackplane 2 }



     smBpMaxPktSize  OBJECT-TYPE
          SYNTAX  INTEGER
	  ACCESS  read-only
          STATUS  mandatory
          DESCRIPTION
	     "The maximum packet size transmitted over the node's
	     Galactica 1 gigabit GBus." 
	  ::= { smBackplane 3 }



     smBpAsyncSlotsEnb  OBJECT-TYPE
          SYNTAX  INTEGER
	  ACCESS  read-only
          STATUS  mandatory
          DESCRIPTION
	     "A bit string returned as an integer that indicates which
	     boards are asynchronous.  The least significant bit
	     represents the board in slot 0."
	  ::= { smBackplane 4 }



     smBpSyncSlotsEnb  OBJECT-TYPE
          SYNTAX  INTEGER
	  ACCESS  read-only
          STATUS  mandatory
          DESCRIPTION
	     "A bit string returned as an integer that indicates which
	     boards are synchronous.  The least significant bit
	     represents the board in slot 0."
	  ::= { smBackplane 5 }



     smBpUtilization  OBJECT-TYPE
          SYNTAX  INTEGER
	  ACCESS  read-only
          STATUS  mandatory
          DESCRIPTION
	     "The current percentage of Galactica 1 gigabit GBus
	     utilization." 
	  ::= { smBackplane 6 }



     smBpTable OBJECT-TYPE
          SYNTAX  SEQUENCE OF SmBpEntry
          ACCESS  not-accessible
          STATUS  mandatory
          DESCRIPTION
             "A table maintaining state information on each board in
	     the node."
          ::= { smBackplane 7 }

     smBpEntry OBJECT-TYPE
          SYNTAX  SmBpEntry
          ACCESS  not-accessible
          STATUS  mandatory
          DESCRIPTION
             "Information maintained on a single board."
          INDEX   { smBpIndex }
          ::= { smBpTable 1 }

     SmBpEntry ::=
          SEQUENCE {
               smBpIndex
                  INTEGER,
	       smBpTableEnable
	          INTEGER,
	       smBpTableJabber
	          INTEGER,
	       smBpTableClearJabber
	          INTEGER
               }


     smBpIndex  OBJECT-TYPE
          SYNTAX  INTEGER (1..9)
	  ACCESS  read-only
          STATUS  mandatory
          DESCRIPTION
	     "The slot number of the board."
	  ::= { smBpEntry 1 }


     smBpTableEnable  OBJECT-TYPE
          SYNTAX  INTEGER {
		     enabled(1),
		     disabled(2)
		  }
	  ACCESS  read-only
          STATUS  mandatory
          DESCRIPTION
	     "The current operational state of the board as viewed by
	     the System Management board."
	  ::= { smBpEntry 2 }




     smBpTableJabber  OBJECT-TYPE
          SYNTAX  INTEGER {
		     true(1),
		     false(2)
		  }
	  ACCESS  read-only
          STATUS  mandatory
          DESCRIPTION
	     "True indicates that the board transmitted a packet that
	     was larger than the maximum packet size and was disabled
	     from the Galactica 1 gigabit GBus by the System
	     Management board.  This state will not be automatically
	     re-set.  The board cannot be re-enabled until manual
	     intervention is taken by setting the smBpTableClearJabber
	     object as defined below." 
	  ::= { smBpEntry 3 }




     smBpTableClearJabber  OBJECT-TYPE
          SYNTAX  INTEGER
	  ACCESS  read-write
          STATUS  mandatory
          DESCRIPTION
	     "When read this object always returns 1.  When set to any
	     value, the System Manager will clear the smBpTableJabber
	     object allowing the board to be re-enabled onto the
	     Galactica 1 gigabit GBus." 
	  ::= { smBpEntry 4 }




     -- systemManagement.powerSupply group

     smPowerSupply   OBJECT IDENTIFIER ::= { systemManagement 4 }


     smSupplyPresent  OBJECT-TYPE
          SYNTAX  INTEGER
	  ACCESS  read-only
          STATUS  mandatory
          DESCRIPTION
	     "A bit string returned as an integer that represents the
	     presence of the power supplies.  The lease significant
	     bit represents power supply 1 which the leftmost power supply."
	  ::= { smPowerSupply 1 }




     smSupplyType  OBJECT-TYPE
          SYNTAX  INTEGER
	  ACCESS  read-only
          STATUS  mandatory
          DESCRIPTION
	     "A bit string returned as an integer that indicates the
	     type of power supply present.  Two bits are assigned to
	     each power supply with the 2 least significant bits
	     representing power supply 1.  The bits are encoded such
	     that:
	     		00  invalid
			01  No supply present
			10  DC supply
			11  AC supply"
	  ::= { smPowerSupply 2 }



     smSupplyAcOk  OBJECT-TYPE
          SYNTAX  INTEGER
	  ACCESS  read-only
          STATUS  mandatory
          DESCRIPTION
	     "A bit string returned as an integer that indicates the
	     status of the AC power units.  The least significant bit
	     represents power supply 1."
	  ::= { smPowerSupply 3 }

     smSupplyDcOk  OBJECT-TYPE
          SYNTAX  INTEGER
	  ACCESS  read-only
          STATUS  mandatory
          DESCRIPTION
	     "A bit string returned as an integer that indicates the
	     status of the DC power units.  The least significant bit
	     represents power supply 1."
	  ::= { smPowerSupply 4 }

	smSupplyTable  OBJECT-TYPE
		SYNTAX  SEQUENCE OF SmSupplyTableEntry
		ACCESS  not-accessible
		STATUS  mandatory
		DESCRIPTION
			"A table of strings describing the status of the chassis power
			supplies."
	::= { smPowerSupply 5 }
     
	smSupplyTableEntry  OBJECT-TYPE
		SYNTAX  SmSupplyTableEntry
		ACCESS  not-accessible
		STATUS  mandatory
		DESCRIPTION
			"The status of one power supply in the chassis."
		INDEX  { smSupplyTableIndex }
	::= { smSupplyTable 1 }
     
	SmSupplyTableEntry ::=
		SEQUENCE {
			smSupplyTableIndex
				INTEGER,
			smSupplyTableStatus
				DisplayString
		}
     
	smSupplyTableIndex  OBJECT-TYPE
		SYNTAX  INTEGER (1..4)
		ACCESS  read-only
		STATUS  mandatory
		DESCRIPTION
			"The number of the power supply in the chassis, numbered from
			left to right."
	::= { smSupplyTableEntry 1 }

	smSupplyTableStatus  OBJECT-TYPE
		SYNTAX  DisplayString (SIZE (0..255))
		ACCESS  read-only
		STATUS  mandatory
		DESCRIPTION
			"A text description of the status of the power supply.
			One of: 'NOT PRESENT', 'OFF', 'ON' or 'FAILURE'."
	::= { smSupplyTableEntry 2 }


	-- systemManagement.modem group

	smModem   OBJECT IDENTIFIER ::= { systemManagement 5 }


	smModemType  OBJECT-TYPE
		SYNTAX  INTEGER {
			internal-japan-2400-baud(1),
			internal-usa-2400-baud(2)
		}
		ACCESS  read-only
		STATUS  mandatory
		DESCRIPTION
			"The modem type present on the node's System Management board."
	::= { smModem 1 }
     
	smModemCallBackEnable  OBJECT-TYPE
		SYNTAX  INTEGER {
			enabled(1),
			disabled(2)
		}
		ACCESS  read-write
		STATUS  mandatory
		DESCRIPTION
			"Enables and disables the call-back feature of the modem.
			If enabled the modem will answer a call, then hang up and dial
			the number in smModemCallBackNumber. If disabled the modem
			will not hang up on any calls."
	::= { smModem 2 }
     
	smModemCallBackNumber  OBJECT-TYPE
		SYNTAX  DisplayString (SIZE (0..255))
		ACCESS  read-write
		STATUS  mandatory
		DESCRIPTION
			"A Hayes style dial string that the internal modem uses if
			call-back is enabled. The string should not contain the 'ATD'
			characters, but a leading 'P' may be used to initiate pulse
			dialing if needed."
	::= { smModem 3 }
	


     -- the following are all under the starbridge subtree
     
     -- starbridge.configuration group


     sbConfiguration   OBJECT IDENTIFIER ::= { starbridge 1 }

     sbCfgManufactureDate  OBJECT-TYPE
          SYNTAX  DisplayString (SIZE (0..255))
	  ACCESS  read-only
          STATUS  mandatory
          DESCRIPTION
	     "The manufacture date of this Starbridge board."
	  ::= { sbConfiguration 1 }





     sbCfgType  OBJECT-TYPE
          SYNTAX  INTEGER {
	             starbridge-board(2)
		  }
	  ACCESS  read-only
          STATUS  mandatory
          DESCRIPTION
	     "The type of board"
	  ::= { sbConfiguration 2 }



     sbCfgHardwareRev  OBJECT-TYPE
          SYNTAX  DisplayString (SIZE (0..255))
	  ACCESS  read-only
          STATUS  mandatory
          DESCRIPTION
	     "The hardware revision number of this Starbridge board."
	  ::= { sbConfiguration 3 }



     sbCfgSerialNumber  OBJECT-TYPE
          SYNTAX  DisplayString (SIZE (0..255))
	  ACCESS  read-only
          STATUS  mandatory
          DESCRIPTION
	     "The serial number of this Starbridge board."
	  ::= { sbConfiguration 4 }



     sbCfgNumberIfBoards  OBJECT-TYPE
          SYNTAX  INTEGER
	  ACCESS  read-only
          STATUS  mandatory
          DESCRIPTION
	     "The number of interface cards on this module."
	  ::= { sbConfiguration 5 }




     sbCfgIfBd1Type  OBJECT-TYPE
          SYNTAX  INTEGER {
                   thicknet-dte(1),
                   thicknet-dce(2),
                   thinnet(3),
                   twisted-pair(4),
                   foirl(5),
                   ten-base-f(6)
                }
	  ACCESS  read-only
          STATUS  mandatory
          DESCRIPTION
	     "The interface type of interface card 1."
	  ::= { sbConfiguration 6 }



     sbCfgIfBd1Rev  OBJECT-TYPE
          SYNTAX  DisplayString (SIZE (0..255))
	  ACCESS  read-only
          STATUS  mandatory
          DESCRIPTION
	     "The hardware revision number of interface card 1."
	  ::= { sbConfiguration 7 }



     sbCfgIfBd1SerialNum  OBJECT-TYPE
          SYNTAX  DisplayString (SIZE (0..255))
	  ACCESS  read-only
          STATUS  mandatory
          DESCRIPTION
	     "The serial number of interface card 1."
	  ::= { sbConfiguration 8 }



     sbCfgIfBd1NumPorts  OBJECT-TYPE
          SYNTAX  INTEGER
	  ACCESS  read-only
          STATUS  mandatory
          DESCRIPTION
	     "The number of ports contained on interface card 1."
	  ::= { sbConfiguration 9 }




     sbCfgIfBd2Type  OBJECT-TYPE
          SYNTAX  INTEGER {
                   thicknet-dte(1),
                   thicknet-dce(2),
                   thinnet(3),
                   twisted-pair(4),
                   foirl(5),
                   ten-base-f(6)
                }
	  ACCESS  read-only
          STATUS  mandatory
          DESCRIPTION
	     "The interface type of interface card 2."
	  ::= { sbConfiguration 10 }



     sbCfgIfBd2Rev  OBJECT-TYPE
          SYNTAX  DisplayString (SIZE (0..255))
	  ACCESS  read-only
          STATUS  mandatory
          DESCRIPTION
	     "The hardware revision number of interface card 2."
	  ::= { sbConfiguration 11 }



     sbCfgIfBd2SerialNum  OBJECT-TYPE
          SYNTAX  DisplayString (SIZE (0..255))
	  ACCESS  read-only
          STATUS  mandatory
          DESCRIPTION
	     "The serial number of interface card 2."
	  ::= { sbConfiguration 12 }



     sbCfgIfBd2NumPorts  OBJECT-TYPE
          SYNTAX  INTEGER
	  ACCESS  read-only
          STATUS  mandatory
          DESCRIPTION
	     "The number of ports contained on interface card 2."
	  ::= { sbConfiguration 13 }



     sbCfgFlashMemorySize  OBJECT-TYPE
          SYNTAX  INTEGER
	  ACCESS  read-only
          STATUS  mandatory
          DESCRIPTION
	     "Number of bytes of flash memory on this Starbridge board."
	  ::= { sbConfiguration 14 }



     sbCfg68kRamSize  OBJECT-TYPE
          SYNTAX  INTEGER
	  ACCESS  read-only
          STATUS  mandatory
          DESCRIPTION
	     "Management software RAM size on this Starbridge board."
	  ::= { sbConfiguration 15 }



     sbCfg960RamSize  OBJECT-TYPE
          SYNTAX  INTEGER
	  ACCESS  read-only
          STATUS  mandatory
          DESCRIPTION
	     "Packet switch software RAM size on this Starbridge board."
	  ::= { sbConfiguration 16 }



     sbCfgSonicRamSize  OBJECT-TYPE
          SYNTAX  INTEGER
	  ACCESS  read-only
          STATUS  mandatory
          DESCRIPTION
	     "Size of the RAM used by the Ethernet Controllers (Sonic)
	     for packet processing.."
	  ::= { sbConfiguration 17 }



     sbCfgHasherCacheTagSize  OBJECT-TYPE
          SYNTAX  INTEGER
	  ACCESS  read-only
          STATUS  mandatory
          DESCRIPTION
	     "The number of bytes in the hasher cache on this
	     Starbridge board.  Each address used 6 bytes."
	  ::= { sbConfiguration 18 }



     sbCfgDualPortRamSize  OBJECT-TYPE
          SYNTAX  INTEGER
	  ACCESS  read-only
          STATUS  mandatory
          DESCRIPTION
	     "The size of the dual port RAM used by the Galactica 
	     1 gigabit GBus on this Starbridge board."
	  ::= { sbConfiguration 19 }



     sbCfgBootRev  OBJECT-TYPE
          SYNTAX  DisplayString (SIZE (0..255))
	  ACCESS  read-only
          STATUS  mandatory
          DESCRIPTION
	     "Revision number and date of the boot software on this
	     Starbridge board."
	  ::= { sbConfiguration 20 }



     sbCfg68kRev  OBJECT-TYPE
          SYNTAX  DisplayString (SIZE (0..255))
	  ACCESS  read-only
          STATUS  mandatory
          DESCRIPTION
	     "Revision number and date of the management boot ROM
	     software on this Starbridge board."
	  ::= { sbConfiguration 21 }



     sbCfg960Rev  OBJECT-TYPE
          SYNTAX  DisplayString (SIZE (0..255))
	  ACCESS  read-only
          STATUS  mandatory
          DESCRIPTION
	     "Revision number and date of the packet switch software
	     on this Starbridge board."
	  ::= { sbConfiguration 22 }



     sbCfgModulePartNumber  OBJECT-TYPE
          SYNTAX  DisplayString (SIZE (0..255))
	  ACCESS  read-only
          STATUS  mandatory
          DESCRIPTION
	     "The Artel part number for this Starbridge module."
	  ::= { sbConfiguration 23 }



     sbCfgModuleSerialNumber  OBJECT-TYPE
          SYNTAX  DisplayString (SIZE (0..255))
	  ACCESS  read-only
          STATUS  mandatory
          DESCRIPTION
	     "The Artel serial number for this Starbridge module."
	  ::= { sbConfiguration 24 }



     sbCfgStoreFlashRev  OBJECT-TYPE
          SYNTAX  DisplayString (SIZE (0..255))
	  ACCESS  read-only
          STATUS  mandatory
          DESCRIPTION
	     "The version number of the software loaded in the store
	     flash memory bank on this Starbridge board."
	  ::= { sbConfiguration 25 }



     sbCfgExecFlashRev  OBJECT-TYPE
          SYNTAX  DisplayString (SIZE (0..255))
	  ACCESS  read-only
          STATUS  mandatory
          DESCRIPTION
	     "The version number of the software loaded in the
	     executable flash memory bank on this Starbridge board."
	  ::= { sbConfiguration 26 }



	-- starbridge.port group

	sbPort   OBJECT IDENTIFIER ::= { starbridge 3 }
     


	sbPortTable OBJECT-TYPE
		SYNTAX  SEQUENCE OF SbPortEntry
		ACCESS  not-accessible
		STATUS  mandatory
		DESCRIPTION
			"Statistics maintained for the ports on a Starbridge board."
	::= { sbPort 1 }

	sbPortEntry OBJECT-TYPE
		SYNTAX  SbPortEntry
		ACCESS  not-accessible
		STATUS  mandatory
		DESCRIPTION
			"The statics for a particular port on the Starbridge board."
		INDEX   { sbPortIndex }
	::= { sbPortTable 1 }

	SbPortEntry ::=
		SEQUENCE {
			sbPortIndex
				INTEGER,
			sbPortRxMulticastFrames
				Counter,
			sbPortRxBroadcastFrames
				Counter,
			sbPortRxRuntErrors
				Counter,
			sbPortRxBytes
				Counter,
			sbPortTxBytes
				Counter,
			sbPortRxBroadcastStatus
				INTEGER,
			sbPortName
				DisplayString,
			sbPortUtilization
				Gauge,
			sbPortFramesPerSecond
				Gauge,
			sbPortErrorRate
				Gauge,
			sbPortInitStats
				INTEGER
		}

	sbPortIndex  OBJECT-TYPE
		SYNTAX  INTEGER (1..8)
		ACCESS  read-only
		STATUS  mandatory
		DESCRIPTION
			"The port number associated with this port.  Always the
			same as ifIndex."
	::= { sbPortEntry 1 }

	sbPortRxMulticastFrames  OBJECT-TYPE
		SYNTAX  Counter
		ACCESS  read-only
		STATUS  mandatory
		DESCRIPTION
			"The number of multicast frames received on this port."
	::= { sbPortEntry 2 }



     sbPortRxBroadcastFrames  OBJECT-TYPE
          SYNTAX  Counter
	  ACCESS  read-only
          STATUS  mandatory
          DESCRIPTION
	     "The number of broadcast frames received on this port."
	  ::= { sbPortEntry 3 }



     sbPortRxRuntErrors  OBJECT-TYPE
          SYNTAX  Counter
	  ACCESS  read-only
          STATUS  mandatory
          DESCRIPTION
	     "The number of packets received that were smaller than
	     the minimum size packet defined for this port."
	  ::= { sbPortEntry 5 }



     sbPortRxBytes  OBJECT-TYPE
          SYNTAX  Counter
	  ACCESS  read-only
          STATUS  mandatory
          DESCRIPTION
	     "The total number of bytes received on this port."
	  ::= { sbPortEntry 6 }



     sbPortTxBytes  OBJECT-TYPE
          SYNTAX  Counter
	  ACCESS  read-only
          STATUS  mandatory
          DESCRIPTION
	     "The total number of bytes transmitted on this port."
	  ::= { sbPortEntry 7 }



     sbPortRxBroadcastStatus  OBJECT-TYPE
          SYNTAX  INTEGER {
		     enabled(1),
		     disabled(2)
		  }
	  ACCESS  read-write
          STATUS  mandatory
          DESCRIPTION
	     "Administratively enables and disables the receipt of
	     broadcasts on this port." 
	  ::= { sbPortEntry 8 }



	sbPortName  OBJECT-TYPE
		SYNTAX  DisplayString (SIZE (0..255))
		ACCESS  read-write
		STATUS  mandatory
		DESCRIPTION
			"Administratively assigned name for this port."
	::= { sbPortEntry 9 }

	sbPortUtilization  OBJECT-TYPE
		SYNTAX  Gauge
		ACCESS  read-only
		STATUS  mandatory
		DESCRIPTION
			"Port usage over the past ten seconds, expressed as a percentage."
	::= { sbPortEntry 10 }
	  
	sbPortFramesPerSecond  OBJECT-TYPE
		SYNTAX  Gauge
		ACCESS  read-only
		STATUS  mandatory
		DESCRIPTION
			"The number of data frames per second seen by the port."
	::= { sbPortEntry 11 }
	  
	sbPortErrorRate  OBJECT-TYPE
		SYNTAX  Gauge
		ACCESS  read-only
		STATUS  mandatory
		DESCRIPTION
			"Port errors over the past ten seconds, expressed as a percentage."
	::= { sbPortEntry 12 }
	  
	sbPortInitStats  OBJECT-TYPE
		SYNTAX  INTEGER
		ACCESS  read-write
		STATUS  mandatory
		DESCRIPTION
			"This object always returns 1. Setting this object to any value
			causes the port statistics to be cleared."
	::= { sbPortEntry 13 }
	  


     sbPortUnidirectTable OBJECT-TYPE
          SYNTAX  SEQUENCE OF SbPortUnidirectEntry
          ACCESS  not-accessible
          STATUS  mandatory
          DESCRIPTION
             "Table that supports the Artel uni-direct option."
          ::= { sbPort 2 }

     sbPortUnidirectEntry OBJECT-TYPE
          SYNTAX  SbPortUnidirectEntry
          ACCESS  not-accessible
          STATUS  mandatory
          DESCRIPTION
             "The information needed for one uni-direct connection."
          INDEX   { sbPortUnidirectIndex }
          ::= { sbPortUnidirectTable 1 }



     SbPortUnidirectEntry ::=
          SEQUENCE {
               sbPortUnidirectIndex
                  INTEGER,
	       sbPortUnidirectEnable
	          INTEGER
               }


     sbPortUnidirectIndex  OBJECT-TYPE
          SYNTAX  INTEGER (1..4)
	  ACCESS  read-only
          STATUS  mandatory
          DESCRIPTION
	     "The index number assigned to this uni-direct channel.  A
	     unidirect channel consists of 2 ports.
	           Channel 1 consists of port 1 and port 2
		   Channel 2 consists of port 3 and port 4
		   Channel 3 consists of port 5 and port 6
		   Channel 4 consists of port 7 and port 8
	     The odd numbered port is alwasy the receive port and the
	     even numbered port is always the transmit port."
	  ::= { sbPortUnidirectEntry 1 }


     sbPortUnidirectEnable  OBJECT-TYPE
          SYNTAX  INTEGER {
		     enabled(1),
		     disabled(2)
		  }
	  ACCESS  read-write
          STATUS  mandatory
          DESCRIPTION
	     "Administratively enables and disables uni-direct."
	  ::= { sbPortUnidirectEntry 2 }


	-- the following are all under the fddi subtree
     
	-- fddi.configuration group

	fddiConfiguration   OBJECT IDENTIFIER ::= { fddi 1 }

	fddiCfgManufactureDate  OBJECT-TYPE
		SYNTAX  DisplayString (SIZE (0..255))
		ACCESS  read-only
		STATUS  mandatory
		DESCRIPTION
		"The manufacture date of this FDDI board."
	::= { fddiConfiguration 1 }

	fddiCfgType  OBJECT-TYPE
		SYNTAX  INTEGER {
			fddi-board(4)
		}
		ACCESS  read-only
		STATUS  mandatory
		DESCRIPTION
		"The type of board."
	::= { fddiConfiguration 2 }

	fddiCfgHardwareRev  OBJECT-TYPE
		SYNTAX  DisplayString (SIZE (0..255))
		ACCESS  read-only
		STATUS  mandatory
		DESCRIPTION
		"The hardware revision number of this FDDI board."
	::= { fddiConfiguration 3 }

	fddiCfgSerialNumber  OBJECT-TYPE
		SYNTAX  DisplayString (SIZE (0..255))
		ACCESS  read-only
		STATUS  mandatory
		DESCRIPTION
		"The serial number of this FDDI board."
	::= { fddiConfiguration 4 }

	fddiCfgNumberFddiPorts  OBJECT-TYPE
		SYNTAX  INTEGER
		ACCESS  read-only
		STATUS  mandatory
		DESCRIPTION
		"The number of ports on this module."
	::= { fddiConfiguration 5 }

	fddiCfgPPFType  OBJECT-TYPE
		SYNTAX  DisplayString (SIZE (0..255))
		ACCESS  read-only
		STATUS  mandatory
		DESCRIPTION
			"A string describing the type of the FDDI chip set module."
	::= { fddiConfiguration 6 }

	fddiCfgPPFRev  OBJECT-TYPE
		SYNTAX  DisplayString (SIZE (0..255))
		ACCESS  read-only
		STATUS  mandatory
		DESCRIPTION
			"The hardware revision and date of the FDDI chip set module."
	::= { fddiConfiguration 7 }

	fddiCfgPPFSerialNumber  OBJECT-TYPE
		SYNTAX  DisplayString (SIZE (0..255))
		ACCESS  read-only
		STATUS  mandatory
		DESCRIPTION
			"The serial number of the FDDI chip set module."
	::= { fddiConfiguration 8 }

	fddiCfgMediaType  OBJECT-TYPE
		SYNTAX  DisplayString (SIZE (0..255))
		ACCESS  read-only
		STATUS  mandatory
		DESCRIPTION
			"A string describing the media type of the FDDI board. For
			example Multi-mode fiber or Twisted Pair."
	::= { fddiConfiguration 9 }

	fddiCfgFlashMemorySize  OBJECT-TYPE
		SYNTAX  INTEGER
		ACCESS  read-only
		STATUS  mandatory
		DESCRIPTION
			"Number of bytes of flash memory on this FDDI board."
	::= { fddiConfiguration 10 }

     fddiCfg68kRamSize  OBJECT-TYPE
		SYNTAX  INTEGER
		ACCESS  read-only
		STATUS  mandatory
		DESCRIPTION
	     "Management software RAM size on this FDDI board."
	  ::= { fddiConfiguration 11 }

     fddiCfg960RamSize  OBJECT-TYPE
		SYNTAX  INTEGER
		ACCESS  read-only
		STATUS  mandatory
		DESCRIPTION
	     "Packet switch software RAM size on this FDDI board."
	  ::= { fddiConfiguration 12 }

	fddiCfgSonicRamSize  OBJECT-TYPE
		SYNTAX  INTEGER
		ACCESS  read-only
		STATUS  mandatory
		DESCRIPTION
			"Size of the RAM used by the Ethernet Controllers (Sonic)
			for packet processing.."
	::= { fddiConfiguration 13 }

	fddiCfgHasherCacheTagSize  OBJECT-TYPE
		SYNTAX  INTEGER
		ACCESS  read-only
		STATUS  mandatory
		DESCRIPTION
			"The number of bytes in the hasher cache on this
			FDDI board.  Each address used 6 bytes."
	::= { fddiConfiguration 14 }

	fddiCfgDualPortRamSize  OBJECT-TYPE
		SYNTAX  INTEGER
		ACCESS  read-only
		STATUS  mandatory
		DESCRIPTION
			"The size of the dual port RAM used by the Galactica 
			1 gigabit GBus on this FDDI board."
	::= { fddiConfiguration 15 }

	fddiCfgBootRev  OBJECT-TYPE
		SYNTAX  DisplayString (SIZE (0..255))
		ACCESS  read-only
		STATUS  mandatory
		DESCRIPTION
			"Revision number and date of the boot software on this
			FDDI board."
	::= { fddiConfiguration 16 }

	fddiCfg68kRev  OBJECT-TYPE
		SYNTAX  DisplayString (SIZE (0..255))
		ACCESS  read-only
		STATUS  mandatory
		DESCRIPTION
			"Revision number and date of the management boot ROM
			software on this FDDI board."
	::= { fddiConfiguration 17 }

	fddiCfg960Rev  OBJECT-TYPE
		SYNTAX  DisplayString (SIZE (0..255))
		ACCESS  read-only
		STATUS  mandatory
		DESCRIPTION
			"Revision number and date of the packet switch software
			on this FDDI board."
	::= { fddiConfiguration 18 }

	fddiCfgPPFSoftwareRev  OBJECT-TYPE
		SYNTAX  DisplayString (SIZE (0..255))
		ACCESS  read-only
		STATUS  mandatory
		DESCRIPTION
			"Revision number and date of the FDDI chip set module."
	::= { fddiConfiguration 19 }

	fddiCfgModulePartNumber  OBJECT-TYPE
		SYNTAX  DisplayString (SIZE (0..255))
		ACCESS  read-only
		STATUS  mandatory
		DESCRIPTION
			"The Artel part number for this FDDI module."
	::= { fddiConfiguration 20 }

	fddiCfgModuleSerialNumber  OBJECT-TYPE
		SYNTAX  DisplayString (SIZE (0..255))
		ACCESS  read-only
		STATUS  mandatory
		DESCRIPTION
	     "The Artel serial number for this FDDI module."
	::= { fddiConfiguration 24 }

	fddiCfgStoreFlashRev  OBJECT-TYPE
		SYNTAX  DisplayString (SIZE (0..255))
		ACCESS  read-only
		STATUS  mandatory
		DESCRIPTION
			"The version number of the software loaded in the store
			flash memory bank on this FDDI board."
	::= { fddiConfiguration 25 }

	fddiCfgExecFlashRev  OBJECT-TYPE
		SYNTAX  DisplayString (SIZE (0..255))
		ACCESS  read-only
		STATUS  mandatory
		DESCRIPTION
			"The version number of the software loaded in the
			executable flash memory bank on this FDDI board."
	::= { fddiConfiguration 26 }

	
	-- FDDI IP fragmentation group
	
	fddiIpFragmentation   OBJECT IDENTIFIER ::= { fddi 2 }

	fddiIpFragEnabled  OBJECT-TYPE
		SYNTAX  INTEGER {
			enabled(1),
			disabled(2)
		}
		ACCESS  read-write
		STATUS  mandatory
		DESCRIPTION
			"Enables and disables IP fragmentation for the FDDI board."
	::= { fddiIpFragmentation 1 }
	
	
	-- FDDI Port group
	
	fddiPort  OBJECT IDENTIFIER ::= { fddi 3 }
	
	fddiPortTable OBJECT-TYPE
		SYNTAX  SEQUENCE OF FddiPortEntry
		ACCESS  not-accessible
		STATUS  mandatory
		DESCRIPTION
			"Statistics maintained for the ports on a FDDI board."
	::= { fddiPort 1 }

	fddiPortEntry OBJECT-TYPE
		SYNTAX  FddiPortEntry
		ACCESS  not-accessible
		STATUS  mandatory
		DESCRIPTION
			"The statics for a particular port on the FDDI board."
		INDEX   { fddiPortIndex }
	::= { fddiPortTable 1 }

	FddiPortEntry ::=
		SEQUENCE {
			fddiPortIndex
				INTEGER,
			fddiPortRxMcastEnabled
				INTEGER,
			fddiPortNotCopiedOffRingErrs
				Counter,
			fddiPortRingOpCounts
				Counter,
			fddiPortFrameCheckErrs
				Counter
		}

	fddiPortIndex  OBJECT-TYPE
		SYNTAX  INTEGER (1..1)
		ACCESS  read-only
		STATUS  mandatory
		DESCRIPTION
			"The port number associated with this port.  Always the
			same as ifIndex."
	::= { fddiPortEntry 1 }

	fddiPortRxMcastEnabled  OBJECT-TYPE
		SYNTAX  INTEGER {
			enabled(1),
			disabled(2)
		}
		ACCESS  read-only
		STATUS  mandatory
		DESCRIPTION
			"Enables and disables the reception of multicast frames on this
			port."
	::= { fddiPortEntry 2 }

	fddiPortNotCopiedOffRingErrs  OBJECT-TYPE
		SYNTAX  Counter
		ACCESS  read-only
		STATUS  mandatory
		DESCRIPTION
			"Equivalent to the ANSI FDDI attribute fddiMACNotCopied-Ct.
			The count of frames that should have been copied off the
			ring but were not. It is not required that the count be exact."
	::= { fddiPortEntry 3 }

	fddiPortRingOpCounts  OBJECT-TYPE
		SYNTAX  Counter
		ACCESS  read-only
		STATUS  mandatory
		DESCRIPTION
			"Equivalent to the ANSI FDDI attribute fddiMACRingOp-Ct.
			The count of the number of times the ring has entered the
			'Ring Operational' state from the 'Ring Not Operational' state.
			It is not required that this count be exact."
	::= { fddiPortEntry 4 }

	fddiPortFrameCheckErrs  OBJECT-TYPE
		SYNTAX  Counter
		ACCESS  read-only
		STATUS  mandatory
		DESCRIPTION
			"The count of frames copied off the ring which had a bad FCS
			(Frame Check Sequence)."
	::= { fddiPortEntry 5 }

	


	-- the following are all under the trap subtree

	artelTrapAddrTable OBJECT-TYPE
		SYNTAX  SEQUENCE OF ArtelTrapAddrEntry
		ACCESS  not-accessible
		STATUS  mandatory
		DESCRIPTION
			"A table of management systems ready to accept traps
			generated by this node."
	::= { artelTrap 1 }

	artelTrapAddrEntry OBJECT-TYPE
		SYNTAX  ArtelTrapAddrEntry
		ACCESS  not-accessible
		STATUS  mandatory
		DESCRIPTION
			"Information needed to deliver traps to a particular
			management station."
		INDEX   { artelTrapAddrIpDest, artelTrapAddrXPortIndex }
	::= { artelTrapAddrTable 1 }

	ArtelTrapAddrEntry ::=
		SEQUENCE {
			artelTrapAddrIpDest
				IpAddress,
			artelTrapAddrXPortIndex
				OCTET STRING,
			artelTrapAddrUdpDest
				INTEGER,
			artelTrapAddrCommunity
				OCTET STRING,
			artelTrapAddrStatus
				INTEGER
		}

	artelTrapAddrIpDest  OBJECT-TYPE
		SYNTAX  IpAddress
		ACCESS  read-write
		STATUS  mandatory
		DESCRIPTION
			"The IP address of the management agent receiving traps."
	::= { artelTrapAddrEntry 1 }

	artelTrapAddrXPortIndex  OBJECT-TYPE
		SYNTAX  OCTET STRING (SIZE (2))
		ACCESS  read-only
		STATUS  mandatory
		DESCRIPTION
			"This is the UDP address defined as an OCTET STRING of 2
			bytes for the purpose of using it as an instance whoses
			sub-id lengths cannot exceed one byte in length."
	::= { artelTrapAddrEntry 2 }

	artelTrapAddrUdpDest  OBJECT-TYPE
		SYNTAX  INTEGER
		ACCESS  read-write
		STATUS  mandatory
		DESCRIPTION
			"The UDP port number used by the management station to
			receive traps."
	::= { artelTrapAddrEntry 3 }

	artelTrapAddrCommunity  OBJECT-TYPE
		SYNTAX  OCTET STRING (SIZE (0..32))
		ACCESS  read-write
		STATUS  mandatory
		DESCRIPTION
			"The community name expected by the management station
			receiving traps."
	::= { artelTrapAddrEntry 4 }

	artelTrapAddrStatus  OBJECT-TYPE
		SYNTAX  INTEGER {
			other(1),
			invalid(2),
			permanent(3),
			temporary(4)
		}
		ACCESS  read-write
		STATUS  mandatory
		DESCRIPTION
			"Permanent entries will be kept in non-volatile
			ram until the user specifically invalidates the entry.
			Temporary entries will be timed out after a minimum 10
			minute interval.
			Invalid entries will be removed from the table."
	::= { artelTrapAddrEntry 5 }

	artelTrapReportString  OBJECT-TYPE
		SYNTAX  DisplayString (SIZE (0..255))
		ACCESS  read-only
		STATUS  mandatory
		DESCRIPTION
			"When read this will always return a NULL string.  It
			will be returned in varBindList of Artel proprietary
			traps to provide the user with any additional information
			available to the agent."
	::= { artelTrap 2 }

END
