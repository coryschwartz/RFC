-- MIB File Generated on 14-Sep-1995 at 17:36:24

PBDG-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

pbdg OBJECT IDENTIFIER ::= { nas 14 }

pbdgDatagram OBJECT IDENTIFIER ::= { pbdg 1 }

pbdgDatagramTable OBJECT-TYPE
SYNTAX SEQUENCE OF PbdgDatagramEntry
ACCESS not-accessible
STATUS mandatory
DESCRIPTION
"A table containing configuration information for each NAC 
in the NAS chassis that supports packet bus datagrams."
::= { pbdgDatagram 1 }

pbdgDatagramEntry OBJECT-TYPE
SYNTAX PbdgDatagramEntry
ACCESS not-accessible
STATUS mandatory
DESCRIPTION
"There is one Configuration row for each Card in the NAS 
chassis that supports packet bus datagrams."
INDEX { pbdgDatagramIndex }
::= { pbdgDatagramTable 1 }

PbdgDatagramEntry ::=
SEQUENCE {
pbdgDatagramIndex
    INTEGER,
pbdgDatagramSentPkts
    Counter,
pbdgDatagramRcvdPkts
    Counter,
pbdgDatagramBusTimeOuts
    Counter,
pbdgDatagramErrorStatus
    INTEGER
}

pbdgDatagramIndex OBJECT-TYPE
SYNTAX INTEGER
ACCESS read-only
STATUS mandatory
DESCRIPTION
"A unique value for each card in the chassis. The value of 
this object matches the value of the index of the 
corresponding card's entry in the entity table of the 
chassis MIB."
::= { pbdgDatagramEntry 1 }

pbdgDatagramSentPkts OBJECT-TYPE
SYNTAX Counter
ACCESS read-only
STATUS mandatory
DESCRIPTION
"This object contains the number of packet bus datagrams 
sent by this entity."
::= { pbdgDatagramEntry 2 }

pbdgDatagramRcvdPkts OBJECT-TYPE
SYNTAX Counter
ACCESS read-only
STATUS mandatory
DESCRIPTION
"This object contains the number of packet bus datagrams 
received by this entity."
::= { pbdgDatagramEntry 3 }

pbdgDatagramBusTimeOuts OBJECT-TYPE
SYNTAX Counter
ACCESS read-only
STATUS mandatory
DESCRIPTION
"This object contains the number of packet bus timeouts 
experienced by this entity."
::= { pbdgDatagramEntry 4 }

pbdgDatagramErrorStatus OBJECT-TYPE
SYNTAX INTEGER{
  noError(1),
  invalidParm(2),
  socketNotOpened(3),
  noMoreSocket(4),
  ackWaitTimeout(9),
  hwNakRcvd(10),
  otherBusError(11),
  noMemory(14),
  nullPointer(15),
  notInitialized(17),
  failedToRecv(18),
  invalidMsgType(19),
  socketClosed(22),
  noResponse(27),
  noDataToTx(29),
  txPreAck(30),
  txTardyAck(31),
  txBusTimeOut(32),
  rxBusTimeOut(33),
  txTAL(34),
  rxTAL(35),
  txMasterTimeOut(36),
  clkVanished(37),
  clkReturned(38),
  shutdown(39),
  frameError(40),
  xIDTimeOut(41),
  invalidAckMeRtnMarker(45),
  invalidFragmentOffset(46),
  maxRxMsgLengthExceeded(47)
}
ACCESS read-only
STATUS mandatory
DESCRIPTION
"This object reflects the current error status of this 
entity."
::= { pbdgDatagramEntry 5 }

END
