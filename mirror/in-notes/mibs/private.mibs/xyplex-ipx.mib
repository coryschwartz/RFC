XYPLEX-IPX-MIB DEFINITIONS ::= BEGIN
            
                    IMPORTS
                            enterprises
                                    FROM RFC1155-SMI
                            OBJECT-TYPE
                                    FROM RFC1212-CONCISE-MIB;
            
            xyplex          OBJECT IDENTIFIER ::= { enterprises 33 }
            ipx             OBJECT IDENTIFIER ::= { xyplex 15 }
            
            -- Xyplex IPX subgroups
            
            ipxSystem       OBJECT IDENTIFIER ::= { ipx 1 }
            ipxIf           OBJECT IDENTIFIER ::= { ipx 2 }
            ipxNetbios      OBJECT IDENTIFIER ::= { ipx 3 }
            ipxRip          OBJECT IDENTIFIER ::= { ipx 4 }
            ipxSap          OBJECT IDENTIFIER ::= { ipx 5 }
            
            --  this is the MIB module for Xyplex IPX implementations
























            
            
            
            
            
            
            -- the System group
            
            -- Implementation of this group is mandatory for all Xyplex
            -- systems that implement IPX
            
            ipxRouting OBJECT-TYPE
                SYNTAX INTEGER { disabled(1), enabled(2) }
                ACCESS read-write
                STATUS mandatory
                DESCRIPTION
                    "Control for IPX routing services."
                ::= { ipxSystem 1 }


































            
            
            
            
            
            
            -- the Interface group
            
            -- Implementation of this group is mandatory for all Xyplex
            -- systems that implement IPX
            
            ipxIfTable OBJECT-TYPE
                SYNTAX SEQUENCE OF IpxIfEntry
                ACCESS not-accessible
                STATUS mandatory
                DESCRIPTION
                    "A list of IPX interface entries."
                ::= { ipxIf 1 }
            
            ipxIfEntry OBJECT-TYPE
                SYNTAX IpxIfEntry
                ACCESS not-accessible
                STATUS mandatory
                DESCRIPTION
                    "IPX interface parameters and counters."
                INDEX { ipxIfIndex }
                ::= { ipxIfTable 1 }
            
            IpxIfEntry ::=
                SEQUENCE {
                    ipxIfIndex
                        INTEGER,
                    ipxIfState
                        INTEGER,
                    ipxIfNetwork
                        INTEGER,
                    ipxIfFrameStyle
                        INTEGER,
                    ipxIfFramesIn
                        Counter,
                    ipxIfFramesOut
                        Counter,
                    ipxIfErrors
                        Counter,
                    ipxIfTransitDelay
                        INTEGER,
                    ipxIfTransitDelayActual
                        INTEGER
                }
            
            ipxIfIndex OBJECT-TYPE
                SYNTAX INTEGER

            
            
            
            
            
            
                ACCESS read-only
                STATUS mandatory
                DESCRIPTION
                    "An index value that uniquely identifies an IPX 
                    interface.  The interface identified by a particular 
                    value of this index is the same interface as 
                    identified by the same value of ifIndex."
                ::= { ipxIfEntry 1 }
            
            ipxIfState OBJECT-TYPE
                SYNTAX INTEGER { disabled(1), enabled(2) }
                ACCESS read-write
                STATUS mandatory
                DESCRIPTION
                    "Control for IPX routing services for this 
                    interface."
                DEFVAL { enabled }
                ::= { ipxIfEntry 2 }
            
            ipxIfNetwork OBJECT-TYPE
                SYNTAX INTEGER
                ACCESS read-write
                STATUS mandatory
                DESCRIPTION
                    "The IPX network number of the network to which this 
                    interface is attached."
                DEFVAL { 0 }
                ::= { ipxIfEntry 3 }
            
            ipxIfFrameStyle OBJECT-TYPE
                SYNTAX INTEGER { ethernet(1), ieee8022(2) }
                ACCESS read-write
                STATUS mandatory
                DESCRIPTION
                    "Control for the CSMA/CD frame style to use on this 
                    interface."
                DEFVAL { ieee8022 }
                ::= { ipxIfEntry 4 }
            
            ipxIfFramesIn OBJECT-TYPE
                SYNTAX Counter
                ACCESS read-only
                STATUS mandatory
                DESCRIPTION
                    "The number of IPX frames received on this 
                    interface."

            
            
            
            
            
            
                ::= { ipxIfEntry 5 }
            
            ipxIfFramesOut OBJECT-TYPE
                SYNTAX Counter
                ACCESS read-only
                STATUS mandatory
                DESCRIPTION
                    "The number of IPX frames sent on this interface."
                ::= { ipxIfEntry 6 }
            
            ipxIfErrors OBJECT-TYPE
                SYNTAX Counter
                ACCESS read-only
                STATUS mandatory
                DESCRIPTION
                    "The number of IPX errors seen on this interface."
                ::= { ipxIfEntry 7 }
            
            ipxIfTransitDelay OBJECT-TYPE
                SYNTAX INTEGER
                ACCESS read-write
                STATUS mandatory
                DESCRIPTION
                    "The number of 55 millisecond ticks it takes for a 
                    packet to  travel from one destination to another on 
                    the interface.  A value of 0 means that the system 
                    will calculate this value based on the measured 
                    speed of the interface."
                ::= { ipxIfEntry 8 }
            
            ipxIfTransitDelayActual OBJECT-TYPE
                SYNTAX INTEGER     
                ACCESS read-only
                STATUS mandatory
                DESCRIPTION
                    "The number of 55 millisecond ticks it takes for a 
                    packet to travel from one destination to another on 
                    the interface."
                ::= { ipxIfEntry 9 }







            
            
            
            
            
            
            -- the Netbios group
            
            -- Implementation of this group is mandatory for all Xyplex
            -- systems that implement IPX Netbios
            
            ipxNetbiosHopLimit OBJECT-TYPE
                SYNTAX INTEGER (0..255)
                ACCESS read-write
                STATUS mandatory
                DESCRIPTION
                    "Maximum number of hops that an IPX Netbios packet 
                    may make."
                ::= { ipxNetbios 1 }
            
            ipxNetbiosIfTable OBJECT-TYPE
                SYNTAX SEQUENCE OF IpxNetbiosIfEntry
                ACCESS not-accessible
                STATUS mandatory
                DESCRIPTION
                    "A list of IPX interface entries."
                ::= { ipxNetbios 2 }
            
            ipxNetbiosIfEntry OBJECT-TYPE
                SYNTAX IpxNetbiosIfEntry
                ACCESS not-accessible
                STATUS mandatory
                DESCRIPTION
                    "IPX interface parameters and counters."
                INDEX { ipxNetbiosIfIndex }
                ::= { ipxNetbiosIfTable 1 }
            
            IpxNetbiosIfEntry ::=
                SEQUENCE {
                    ipxNetbiosIfIndex
                        INTEGER,
                    ipxIfNetbiosForwarding
                        INTEGER,
                    ipxIfNetbiosIn
                        Counter,
                    ipxIfNetbiosOut
                        Counter
                }
            
            ipxNetbiosIfIndex OBJECT-TYPE
                SYNTAX INTEGER
                ACCESS read-only

            
            
            
            
            
            
                STATUS mandatory
                DESCRIPTION
                    "An index value that uniquely identifies an IPX 
                    interface.  The interface identified by a particular 
                    value of this index is the same interface as 
                    identified by the same value of ifIndex."
                ::= { ipxNetbiosIfEntry 1 }
            
            ipxIfNetbiosForwarding OBJECT-TYPE
                SYNTAX INTEGER { disabled(1), enabled(2) }
                ACCESS read-write
                STATUS mandatory
                DESCRIPTION
                    "Control whether Netbios packet will be forwarded in 
                    or out on this interface."
                DEFVAL { enabled }
                ::= { ipxNetbiosIfEntry 2 }
            
            ipxIfNetbiosIn OBJECT-TYPE
                SYNTAX Counter
                ACCESS read-only
                STATUS mandatory
                DESCRIPTION
                    "The number of IPX Netbios frames received on this 
                    interface."
                ::= { ipxNetbiosIfEntry 3 }
            
            ipxIfNetbiosOut OBJECT-TYPE
                SYNTAX Counter
                ACCESS read-only
                STATUS mandatory
                DESCRIPTION
                    "The number of IPX Netbios frames sent on this 
                    interface."
                ::= { ipxNetbiosIfEntry 4 }
            










            
            
            
            
            
            
            -- the RIP group
            
            -- Implementation of this group is mandatory for all Xyplex
            -- systems that implement IPX RIP
            
            ipxRipIfTable OBJECT-TYPE
                SYNTAX SEQUENCE OF IpxRipIfEntry
                ACCESS not-accessible
                STATUS mandatory
                DESCRIPTION
                    "A list of IPX interface entries."
                ::= { ipxRip 1 }
            
            ipxRipIfEntry OBJECT-TYPE
                SYNTAX IpxRipIfEntry
                ACCESS not-accessible
                STATUS mandatory
                DESCRIPTION
                    "IPX interface parameters and counters."
                INDEX { ipxRipIfIndex }
                ::= { ipxRipIfTable 1 }
            
            IpxRipIfEntry ::=
                SEQUENCE {
                    ipxRipIfIndex
                        INTEGER,
                    ipxIfRipBcst
                        INTEGER,
                    ipxIfRipBcstDiscardTimeout
                        INTEGER,
                    ipxIfRipBcstTimer
                        INTEGER,
                    ipxIfRipIn
                        Counter,
                    ipxIfRipOut
                        Counter,
                    ipxIfRipAgedOut
                        Counter
                }
            
            ipxRipIfIndex OBJECT-TYPE
                SYNTAX INTEGER
                ACCESS read-only
                STATUS mandatory
                DESCRIPTION
                    "An index value that uniquely identifies an IPX 

            
            
            
            
            
            
                            interface.  The interface identified by a particular 
                    value of this index is the same interface as 
                    identified by the same value of ifIndex."
                ::= { ipxRipIfEntry 1 }
            
            ipxIfRipBcst OBJECT-TYPE
                SYNTAX INTEGER { disabled(1), enabled(2) }
                ACCESS read-write
                STATUS mandatory
                DESCRIPTION
                    "Control whether RIP packets will be broadcasted out 
                    this interface."
                DEFVAL { enabled }
                ::= { ipxRipIfEntry 2 }
            
            ipxIfRipBcstDiscardTimeout OBJECT-TYPE
                SYNTAX INTEGER
                ACCESS read-write
                STATUS mandatory
                DESCRIPTION
                    "The number of seconds to wait before discarding 
                    information learned from a RIP broadcast."
                DEFVAL { 180 }
                ::= { ipxRipIfEntry 3 }
            
            ipxIfRipBcstTimer OBJECT-TYPE
                SYNTAX INTEGER
                ACCESS read-write
                STATUS mandatory
                DESCRIPTION
                    "The number of seconds to wait between sending out 
                    RIP broadcasts."
                DEFVAL { 60 }
                ::= { ipxRipIfEntry 4 }
            
            ipxIfRipIn OBJECT-TYPE
                SYNTAX Counter
                ACCESS read-only
                STATUS mandatory
                DESCRIPTION
                    "The number of RIP broadcasts received on this 
                    interface."
                ::= { ipxRipIfEntry 5 }
            
            ipxIfRipOut OBJECT-TYPE
                SYNTAX Counter

            
            
            
            
            
            
                ACCESS read-only
                STATUS mandatory
                DESCRIPTION
                    "The number of RIP broadcasts sent on this 
                    interface."
                ::= { ipxRipIfEntry 6 }
            
            ipxIfRipAgedOut OBJECT-TYPE
                SYNTAX Counter
                ACCESS read-only
                STATUS mandatory
                DESCRIPTION
                    "The number of entries timed out and discarded on 
                    this interface."
                ::= { ipxRipIfEntry 7 }
            
            ipxRipTable OBJECT-TYPE
                SYNTAX SEQUENCE OF IpxRipEntry
                ACCESS not-accessible
                STATUS mandatory
                DESCRIPTION
                    "A list of RIP entries."
                ::= { ipxRip 2 }
            
            ipxRipEntry OBJECT-TYPE
                SYNTAX IpxRipEntry
                ACCESS not-accessible
                STATUS mandatory
                DESCRIPTION
                    "IPX interface parameters and counters."
                INDEX { ipxRipNetwork }
                ::= { ipxRipTable 1 }
            
            IpxRipEntry ::=
                SEQUENCE {
                    ipxRipNetwork
                        INTEGER,
                    ipxRipRouter
                        OCTET STRING,
                    ipxRipInterface
                        INTEGER,
                    ipxRipHops
                        INTEGER,
                    ipxRipTransTime
                        INTEGER,
                    ipxRipAge

            
            
            
            
            
            
                        INTEGER
                }
            
            ipxRipNetwork OBJECT-TYPE
                SYNTAX INTEGER
                ACCESS read-only
                STATUS mandatory
                DESCRIPTION
                    "An IPX network number to which this router knows a 
                    path."
                ::= { ipxRipEntry 1 }
            
            ipxRipRouter OBJECT-TYPE
                SYNTAX OCTET STRING ( SIZE(6) )
                ACCESS read-only
                STATUS mandatory
                DESCRIPTION
                    "The Ethernet address of an IPX router on this 
                    network."
                ::= { ipxRipEntry 2 }
            
            ipxRipInterface OBJECT-TYPE
                SYNTAX INTEGER
                ACCESS read-only
                STATUS mandatory
                DESCRIPTION
                    "The interface to reach the router.  A value of 
                    ifIndex."
                ::= { ipxRipEntry 3 }
            
            ipxRipHops OBJECT-TYPE
                SYNTAX INTEGER
                ACCESS read-only
                STATUS mandatory
                DESCRIPTION
                    "The number of hops to reach the router."
                ::= { ipxRipEntry 4 }
            
            ipxRipTransTime OBJECT-TYPE
                SYNTAX INTEGER
                ACCESS read-only
                STATUS mandatory
                DESCRIPTION
                    "The number of 55 millisecond ticks it takes for a 
                    packet to travel to the router."
                ::= { ipxRipEntry 5 }

            
            
            
            
            
            
            
            ipxRipAge OBJECT-TYPE
                SYNTAX INTEGER
                ACCESS read-only
                STATUS mandatory
                DESCRIPTION
                    "The age of the RIP entry in seconds."
                ::= { ipxRipEntry 6 }






































            
            
            
            
            
            
            -- the SAP group
            
            -- Implementation of this group is mandatory for all Xyplex
            -- systems that implement IPX SAP
            
            ipxSapIfTable OBJECT-TYPE
                SYNTAX SEQUENCE OF IpxSapIfEntry
                ACCESS not-accessible
                STATUS mandatory
                DESCRIPTION
                    "A list of IPX interface entries."
                ::= { ipxSap 1 }
            
            ipxSapIfEntry OBJECT-TYPE
                SYNTAX IpxSapIfEntry
                ACCESS not-accessible
                STATUS mandatory
                DESCRIPTION
                    "IPX interface parameters and counters."
                INDEX { ipxSapIfIndex }
                ::= { ipxSapIfTable 1 }
            
            IpxSapIfEntry ::=
                SEQUENCE {
                    ipxSapIfIndex
                        INTEGER,
                    ipxIfSapBcst
                        INTEGER,
                    ipxIfSapBcstDiscardTimeout
                        INTEGER,
                    ipxIfSapBcstTimer
                        INTEGER,
                    ipxIfSapIn
                        Counter,
                    ipxIfSapOut
                        Counter,
                    ipxIfSapAgedOut
                        Counter
                }
            
            ipxSapIfIndex OBJECT-TYPE
                SYNTAX INTEGER
                ACCESS read-only
                STATUS mandatory
                DESCRIPTION
                    "An index value that uniquely identifies an IPX 

            
            
            
            
            
            
                            interface.  The interface identified by a particular 
                    value of this index is the same interface as 
                    identified by the same value of ifIndex."
                ::= { ipxSapIfEntry 1 }
            
            ipxIfSapBcst OBJECT-TYPE
                SYNTAX INTEGER { disabled(1), enabled(2) }
                ACCESS read-write
                STATUS mandatory
                DESCRIPTION
                    "Control whether SAP packets will be broadcasted out 
                    this interface."
                DEFVAL { enabled }
                ::= { ipxSapIfEntry 2 }
            
            ipxIfSapBcstDiscardTimeout OBJECT-TYPE
                SYNTAX INTEGER
                ACCESS read-write
                STATUS mandatory
                DESCRIPTION
                    "The number of seconds to wait before discarding 
                    information learned from a SAP broadcast."
                DEFVAL { 180 }
                ::= { ipxSapIfEntry 3 }
            
            ipxIfSapBcstTimer OBJECT-TYPE
                SYNTAX INTEGER
                ACCESS read-write
                STATUS mandatory
                DESCRIPTION
                    "The number of seconds to wait between sending out 
                    SAP broadcasts."
                DEFVAL { 60 }
                ::= { ipxSapIfEntry 4 }
            
            ipxIfSapIn OBJECT-TYPE
                SYNTAX Counter
                ACCESS read-only
                STATUS mandatory
                DESCRIPTION
                    "The number SAP broadcasts received on this 
                    interface."
                ::= { ipxSapIfEntry 5 }
            
            ipxIfSapOut OBJECT-TYPE
                SYNTAX Counter

            
            
            
            
            
            
                ACCESS read-only
                STATUS mandatory
                DESCRIPTION
                    "The number SAP broadcasts sent on this interface."
                ::= { ipxSapIfEntry 6 }
            
            ipxIfSapAgedOut OBJECT-TYPE
                SYNTAX Counter
                ACCESS read-only
                STATUS mandatory
                DESCRIPTION
                    "The number entries for this interface discarded due 
                    to aging timeout."
                ::= { ipxSapIfEntry 7 }
            
            ipxSapTable OBJECT-TYPE
                SYNTAX SEQUENCE OF IpxSapEntry
                ACCESS not-accessible
                STATUS mandatory
                DESCRIPTION
                    "A list of SAP entries."
                ::= { ipxSap 2 }
            
            ipxSapEntry OBJECT-TYPE
                SYNTAX IpxSapEntry
                ACCESS not-accessible
                STATUS mandatory
                DESCRIPTION
                    "IPX interface parameters and counters."
                INDEX { ipxSapName, ipxSapType }
                ::= { ipxSapTable 1 }
            
            IpxSapEntry ::=
                SEQUENCE {
                    ipxSapName
                        DisplayString,
                    ipxSapNetwork
                        INTEGER,
                    ipxSapHost
                        OCTET STRING,
                    ipxSapSocket
                        INTEGER,
                    ipxSapInterface
                        INTEGER,
                    ipxSapType
                        INTEGER,

            
            
            
            
            
            
                    ipxSapAge
                        INTEGER
                }
            
            ipxSapName OBJECT-TYPE
                SYNTAX DisplayString (SIZE (48))
                ACCESS read-only
                STATUS mandatory
                DESCRIPTION
                    "The name of the service, null filled."
                ::= { ipxSapEntry 1 }
            
            ipxSapNetwork OBJECT-TYPE
                SYNTAX INTEGER
                ACCESS read-only
                STATUS mandatory
                DESCRIPTION
                    "The IPX network number on which the service's host 
                    resides."
                ::= { ipxSapEntry 2 }
            
            ipxSapHost OBJECT-TYPE
                SYNTAX OCTET STRING ( SIZE(6))
                ACCESS read-only
                STATUS mandatory
                DESCRIPTION
                    "The Ethernet address of the IPX host of the 
                    service."
                ::= { ipxSapEntry 3 }
            
            ipxSapSocket OBJECT-TYPE
                SYNTAX INTEGER
                ACCESS read-only
                STATUS mandatory
                DESCRIPTION
                    "The socket number of the service on the host."
                ::= { ipxSapEntry 4 }
            
            ipxSapInterface OBJECT-TYPE
                SYNTAX INTEGER
                ACCESS read-only
                STATUS mandatory
                DESCRIPTION
                    "The interface of the router in the direction of the 
                    service.  A value of ifIndex."
                ::= { ipxSapEntry 5 }

            
            
            
            
            
            
            
            ipxSapType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service."
                ::= { ipxSapEntry 6 }
            
            ipxSapAge OBJECT-TYPE
                SYNTAX INTEGER
                ACCESS read-only
                STATUS mandatory
                DESCRIPTION
                    "The age of the Sap entry in seconds."
                ::= { ipxSapEntry 7 }
            
END
