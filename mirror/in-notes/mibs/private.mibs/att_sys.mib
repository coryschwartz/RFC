-- SCCS version: "@(#)att_sys.mib	4.1.2.2"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T System MIB for Customer Network Management
--	


	ATT-CNM-SYSTEM-MIB DEFINITIONS ::= BEGIN

	IMPORTS
		enterprises, TimeTicks
			FROM RFC1155-SMI
		DisplayString
			FROM RFC1213-MIB
		OBJECT-TYPE
			FROM RFC-1212;

	--
	-- Object Identifiers
	--

	att-2			OBJECT IDENTIFIER ::= { enterprises 74 }
	att-products		OBJECT IDENTIFIER ::= { att-2 1 }
	att-mgmt		OBJECT IDENTIFIER ::= { att-2 2 }
	att-cnmAgent		OBJECT IDENTIFIER ::= { att-products 9 }
	att-cnm			OBJECT IDENTIFIER ::= { att-mgmt 15 }
	att-cnm-system		OBJECT IDENTIFIER ::= { att-cnm 1 }
	att-cnm-interfaces	OBJECT IDENTIFIER ::= { att-cnm 2 }


	--
	-- the System group of objects (att-cnm-system) provide
	-- information relevant to the entire system.
	--


	attCNMsysDescr OBJECT-TYPE
		SYNTAX  DisplayString(SIZE(0..255))
		ACCESS  read-only
		STATUS  mandatory
		DESCRIPTION
			"A printable ASCII string that is a textual
			description of this system. This value typically
			includes the full name and version identification
			of the system.

			This identification can be used to distinguish
			this system from other systems for the purpose of
			fault identification/isolation, trouble reporting etc."
		::= { att-cnm-system 1 }

	attCNMsysObjectID OBJECT-TYPE
		SYNTAX  OBJECT IDENTIFIER
		ACCESS  read-only
		STATUS  mandatory
		DESCRIPTION
			"The vendor's authoritative identification of the
			network management subsystem contained in the entity.

			This value is allocated within the SMI enterprises
			subtree (1.3.6.1.4.1) and provides an easy and
			unambiguous means for determining `what kind of box'
			is being managed.  For example, if vendor `Flintstones,
			Inc.' was assigned the subtree 1.3.6.1.4.1.4242, it
			could assign the identifier 1.3.6.1.4.1.4242.1.1 to
			its `Fred Router'.

			This identification can be used to distinguish this
			system from other systems."
		::= { att-cnm-system 2 }

	attCNMsysUpTime OBJECT-TYPE
		SYNTAX  TimeTicks
		ACCESS  read-only
		STATUS  mandatory
		DESCRIPTION
			"The time (in hundredths of a second) since the
			SNMP interface portion of the system was last
			re-initialized.

			This value may be used to determine the last time
			this system was re-initialized (i.e. the most
			recent reset for the SNMP interface)."
		::= { att-cnm-system 3 }

	attCNMsysContact OBJECT-TYPE
		SYNTAX  DisplayString(SIZE(0..255))
		ACCESS  read-only
		STATUS  mandatory
		DESCRIPTION
			"The textual identification of the contact person(s)
			or organization(s) for this system, along with
			information on how to contact them."
		::= { att-cnm-system 4 }

	attCNMsysName OBJECT-TYPE
		SYNTAX  DisplayString(SIZE(0..255))
		ACCESS  read-only
		STATUS  mandatory
		DESCRIPTION
			"An administratively-assigned name for this
			system. By convention, this is the system's
			fully-qualified domain name.

			This variable distinguishes this system from other
			systems in the network."
		::= { att-cnm-system 5 }

	attCNMsysLocation OBJECT-TYPE
		SYNTAX  DisplayString(SIZE(0..255))
		ACCESS  read-only
		STATUS  mandatory
		DESCRIPTION
			"The physical location of this system.

			This variable distinguishes this system from others
			for location purposes."
		::= { att-cnm-system 6 }

	attCNMsysServices OBJECT-TYPE
		SYNTAX  INTEGER(0..127)
		ACCESS  read-only
		STATUS  mandatory
		DESCRIPTION
			"A value which indicates the set of services offered
			by the managed network elements.

			The value is a sum.  This sum initially takes the
			value zero, Then, for each layer, L, in the range
			1 through 7, that this node performs transactions
			for, 2 raised to (L - 1) is added to the sum.  For
			example, a node which performs primarily routing
			functions would have a value of 4 (2^(3-1)).  In
			contrast, a node which is a host offering
			application services would have a value of 72
			(2^(4-1) + 2^(7-1)).  Note that in the context of
			the Internet suite of protocols, values should be
			calculated accordingly:

				layer  functionality
				 1	physical (e.g., repeaters)
				 2	datalink/subnetwork (e.g., bridges)
				 3	internet (e.g., IP gateways)
				 4	end-to-end  (e.g., IP hosts)
				 7	applications (e.g., mail relays)

			For systems including OSI protocols, layers 5 and
			6 may also be counted.

			For SMDS and Frame Relay Service, this agent will
			return a value of 2 which indicates that the managed
			network elements offer a subnetwork-level service."
		::= { att-cnm-system 7 }


	--
	-- the Interfaces group of objects (att-cnm-interfaces) provide
	-- general information about all the interfaces supported by
	-- this system. It includes:
	--
	--	the Interfaces Configuration table
	--	the Interfaces Status table
	--


	attCNMifNumber OBJECT-TYPE
		SYNTAX  INTEGER
		ACCESS  read-only
		STATUS  mandatory
		DESCRIPTION
			"The number of network interfaces (regardless
			of their current state) that can be managed
			by a specific subscriber."
		::= { att-cnm-interfaces 1 }


	-- the Interfaces Configuration table

	-- This table provides configuration information on the
	-- interfaces managed by this system.


	attCNMifConfigTable OBJECT-TYPE
		SYNTAX	SEQUENCE OF AttCNMifConfigEntry
		ACCESS  not-accessible
		STATUS  mandatory
		DESCRIPTION
			"A list of entries containing general information
			for all interfaces managed by this system."
		::= { att-cnm-interfaces 2 }

	attCNMifConfigEntry OBJECT-TYPE
		SYNTAX  AttCNMifConfigEntry
		ACCESS  not-accessible
		STATUS  mandatory
		DESCRIPTION
			"An entry containing general configuration
			information for a particular interface."
		INDEX	{ attCNMifConfigIndex }
		::= { attCNMifConfigTable 1 }

	AttCNMifConfigEntry ::=
		SEQUENCE {
		    attCNMifConfigIndex
			INTEGER,
		    attCNMifDescr
			DisplayString,
		    attCNMifType
			INTEGER,
		    attCNMifMtu
			INTEGER,
		    attCNMifSpeed
			Gauge,
		    attCNMifContact
			DisplayString,
		    attCNMifLocation
			DisplayString,
		    attCNMifSubscriber
			DisplayString
		}

	attCNMifConfigIndex OBJECT-TYPE
		SYNTAX  INTEGER
		ACCESS  read-only
		STATUS  mandatory
		DESCRIPTION
			"A unique value assigned to each interface by
			the administrator of this system."
		::= { attCNMifConfigEntry 1 }

	attCNMifDescr OBJECT-TYPE
		SYNTAX  DisplayString(SIZE(0..255))
		ACCESS  read-only
		STATUS  mandatory
		DESCRIPTION
			"A textual string containing information about this
			interface.

			This string typically contains the name of the service
			provider, the service offered by this interface,
			and the name of the subscriber to this interface."
		::= { attCNMifConfigEntry 2 }

	attCNMifType OBJECT-TYPE
		SYNTAX	INTEGER {
			    other(1),
			    sip(31),
			    frame-relay(32)
			}
		ACCESS	read-only
		STATUS	mandatory
		DESCRIPTION
			"The type of interface being managed."
		::= { attCNMifConfigEntry 3 }

	attCNMifMtu OBJECT-TYPE
		SYNTAX	INTEGER
		ACCESS	read-only
		STATUS	mandatory
		DESCRIPTION
			"The size of the largest data PDU which can be
			sent/received on the interface, specified in
			octets.

			For SMDS, this value represents the maximum L3
			PDU size that is supported on this interface."
		::= { attCNMifConfigEntry 4 }

	attCNMifSpeed OBJECT-TYPE
		SYNTAX	Gauge
		ACCESS	read-only
		STATUS	mandatory
		DESCRIPTION
			"An estimate of the interface's current nominal
			bandwidth in bits per second."
		::= { attCNMifConfigEntry 5 }

	attCNMifContact OBJECT-TYPE
		SYNTAX	DisplayString(SIZE(0..255))
		ACCESS	read-only
		STATUS	mandatory
		DESCRIPTION
			"A printable ASCII string that identifies the
			contact person(s) or organization(s) responsible
			for support of this interface."
		::= { attCNMifConfigEntry 6 }

	attCNMifLocation OBJECT-TYPE
		SYNTAX	DisplayString(SIZE(0..255))
		ACCESS	read-only
		STATUS	mandatory
		DESCRIPTION
			"A printable ASCII string that identifies the
			physical location of the switching system that
			terminates this interface."
		::= { attCNMifConfigEntry 7 }

	attCNMifSubscriber OBJECT-TYPE
		SYNTAX	DisplayString(SIZE(0..255))
		ACCESS	read-only
		STATUS	mandatory
		DESCRIPTION
			"A printable ASCII string that identifies the
			contact person(s) or organization(s) that have
			subscribed to this interface."
		::= { attCNMifConfigEntry 8 }


	-- the Interfaces Status table

	-- This table contains status information on the
	-- interfaces supported by this system.


	attCNMifStatusTable OBJECT-TYPE
		SYNTAX	SEQUENCE OF AttCNMifStatusEntry
		ACCESS  not-accessible
		STATUS  mandatory
		DESCRIPTION
			"A list of entries containing status information
			for all interfaces managed by this system."
		::= { att-cnm-interfaces 3 }

	attCNMifStatusEntry OBJECT-TYPE
		SYNTAX  AttCNMifStatusEntry
		ACCESS  not-accessible
		STATUS  mandatory
		DESCRIPTION
			"An entry containing status information for a
			particular interface."
		INDEX	{ attCNMifStatusIndex }
		::= { attCNMifStatusTable 1 }

	AttCNMifStatusEntry ::=
		SEQUENCE {
		    attCNMifStatusIndex
			INTEGER,
		    attCNMifAdminStatus
			INTEGER,
		    attCNMifOperStatus
			INTEGER
		}

	attCNMifStatusIndex OBJECT-TYPE
		SYNTAX  INTEGER
		ACCESS  read-only
		STATUS  mandatory
		DESCRIPTION
			"A unique value for each interface. The interface
			identified by a particular value of this index is
			the same interface as identified by the same value
			of an attCNMifConfigIndex object instance."
		::= { attCNMifStatusEntry 1 }

	attCNMifAdminStatus OBJECT-TYPE
		SYNTAX	INTEGER {
			    up(1),
			    down(2),
			    testing(3),
			    unknown(4)
			} 
		ACCESS	read-only
		STATUS	mandatory
		DESCRIPTION
			"The desired state of this interface."
		::= { attCNMifStatusEntry 2 }

	attCNMifOperStatus OBJECT-TYPE
		SYNTAX	INTEGER {
			    up(1),
			    down(2),
			    testing(3),
			    unknown(4)
			}
		ACCESS	read-only
		STATUS	mandatory
		DESCRIPTION
			"The current operational state of this interface."
		::= { attCNMifStatusEntry 3 }

	END
